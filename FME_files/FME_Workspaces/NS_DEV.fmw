FME workspace NS_DEV.fmw
Title: NS_DEV
Description: Description 
This workbench read and trasform all the metadata for the province New Scotia (NS).
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...).
METADATA_OVERWRITE: Enable the overwite of the PyCSW.  Can take two values: Yes: Overwrite the content of the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
IN_TBS_JSON_TEMPLATE_DIR: Source directory of the root JSON templates. Defined as: \JSON_TEMPLATES
LOG_FILE: Output log file. Defined as: \NS\LOG\NS.log
OUT_JSON_LOCAL_DIR: Source directory to output JSON files. Defined as: \NS\JSON_LOCAL
OUT_XLS_NOTIFICATION: Source directory to output excel files. Defined as: \NS\XLS
OUT_XML_FAILED_DIR: Source directory to output failed XML files. Defined as: \NS\XML_FAILED
OUT_XML_LOCAL_DIR: Source directory to output Local Source XML files. Defined as: \NS\XML_LOCAL
OUT_XML_PASSED_DIR: Source directory to output passedXML files. Defined as: \NS\XML_PASSED
SAMPLE_SIZE: Number of features to process. Zero (0) means process all the features. A number n greater than 0 means sample or process only the first n features.
URL_VALIDATION : Indicates to validate or not created URL. (Should be Yes for prod)

Parameters:
- ACTIVATE_GEO = Yes
- ACTIVATE_NON_GEO = No
- ACTIVATE_TRANSLATION = Yes
- CATALOGUE_READER_SELECT = Yes
- FORCED_PYCSW_URL =
- IN_FFS_TESTING_FILE =
- LOCAL_SOURCE_METADATA_DELTA_FINDER = No
- LOCAL_WRITER = Yes
- P-T_ABBR = NS
- METADATA_OVERWRITE = YES
- IN_OUT_WORKING_DIR = $(FME_SHAREDRESOURCE_DATA)\PT_Harvester
- SAMPLE_SIZE = 0
- URL_VALIDATION = Yes
- IN_CSV_LOOKUPTABLES_DIR = $(IN_OUT_WORKING_DIR)\LOOKUP_TABLES
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Resource Data

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Socrata_BoundingBoxExtractor: SOCRATA_BOUNDING_BOX_EXTRACTOR
    DOMAIN = http://data.novascotia.ca
    SocrataAppToken = FL3Cxsebg0Vf6JQ0CnbMujHkQ
    URL_VALIDATION = $(URL_VALIDATION)
    feature_output -> METADATA_VALUE_MAPPER_NG [DATA_INPUT]
Junction_4
    -> AWS_TRANSLATE_2
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
VariableRetriever_12
    SCOPE = Global
    VALUE_ATTR = _timestamp
    VARNAME = _timestamp
    -> invalid_metadata (writer XLSXW_1)
invalid_metadata (writer XLSXW_1)
    attributes: id auto(20)
Note: Log deleted features
DELETED_RECORDS_NONE_GEO00 (writer XLSXW_1)
    attributes: id auto(20)

Bookmark: lecture des données du portail socrata, filtrage de licence et fusion des métadonnées de vue externe
Creator_3
    GEOMTYPE = Geometry Object
    NUM = 1
    CREATED -> DateTimeStamper
DateTimeStamper
    DATETIME_ATTR = _toto
    STAMP_TYPE = date
    TIMEZONE = local
    -> VariableSetter
VariableSetter
    SCOPE = Global
    VALUE = @Value(_toto)
    VARNAME = _timestamp
    -> Tester_6
Tester_6
    BOOL_OP = OR
    COMPOSITE_TEST = 1
    TEST_CLAUSE = TEST @UpperCase($(CATALOGUE_READER_SELECT)) = YES
    TEST_MODE = TEST
    PASSED -> SOCRATA_READER_NG
    FAILED -> FeatureReader_2 [INITIATOR]
SOCRATA_READER_NG
    DOMAIN = https://data.novascotia.ca
    -> ATTRIBUTE_VALUE_TEXT_CLEANER
FeatureReader_2
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER
ATTRIBUTE_VALUE_TEXT_CLEANER
    -> AttributeExposer_3
AttributeExposer_3
    ATTR_LIST = id
    -> NullAttributeMapper
NullAttributeMapper
    ATTRCHOICE = Selected Attributes
    ATTRLIST = licenseId
    NEW_VALUE = none
    NULL_TREATMENT = New Value
    SOURCE_ATTR_VAL = Null Empty "Missing (Selected Attributes Only)"
    -> AttributeExposer_11
AttributeExposer_11
    ATTR_LIST = id,name
    -> LICENSE_FILTER_NG
Note: LICENSE_NS
LICENSE_FILTER_NG
    FEATURE_TYPE = License_NS
    IN_CSV_LOOKUP_TABLES_DIR = $(IN_CSV_LOOKUPTABLES_DIR)
    LICENSE_ATT = @Value(licenseId)
    P-T_ABBR = $(P-T_ABBR)
    LICENSE_FILTER_PASSED -> Socrata_MetadataMerger
    UNKNOWN_LICENSE -> VariableRetriever_8
Socrata_MetadataMerger: SOCRATA_METADATA_MERGER
    DOMAIN = https://data.novascotia.ca
    -> DEFAULT_ATTRIBUTE_MAPPER_NG
    UnmergedAdvancedView -> VariableRetriever_4
VariableRetriever_4
    SCOPE = Global
    VALUE_ATTR = _timestamp
    VARNAME = _timestamp
    -> unmergedAdvancedView (writer XLSXW_1)
unmergedAdvancedView (writer XLSXW_1)
    attributes: url string(200), format string(200), _seriesID string(200), _timestamp string(200)
VariableRetriever_8
    SCOPE = Global
    VALUE_ATTR = _timestamp
    VARNAME = _timestamp
    -> unknown_licence (writer XLSXW_1)
unknown_licence (writer XLSXW_1)
    attributes: license_id string(200), id string(200), title string(200)

Bookmark: Transformation vers modèle de travail et ajout des valeurs par défaults
Note: DEFAULT NS
DEFAULT_ATTRIBUTE_MAPPER_NG
    FEATURE_TYPE = Default_NS
    IN_CSV_LOOKUP_TABLES_DIR = $(IN_CSV_LOOKUPTABLES_DIR)
    P-T_ABBR = $(P-T_ABBR)
    -> AttributeExposer_14
EXTRACT_COLLECTION_START_END_DATE
    CSV_PATH = $(IN_CSV_LOOKUPTABLES_DIR)
    DATE_EXTENT = @Value(range_collection_date)
    FEATURE_TYPE = NS_Manual_end_start_collection_date
    PT = $(P-T_ABBR)
    -> AttributeExposer_16
    Unworking_extent -> VariableRetriever_6
VariableRetriever_6
    SCOPE = Global
    VALUE_ATTR = _timestamp
    VARNAME = _timestamp
    -> Unworking_date_collection_extent (writer XLSXW_1)
Unworking_date_collection_extent (writer XLSXW_1)
    attributes: unmatched_date_extent string(200)

Bookmark: Date conversion
AttributeExposer_14
    ATTR_LIST = publicationDate,createdAt,viewLastModified
    -> DateTimeConverter
Note: Formats all date fields to ISO yyyy-mm-dd
DateTimeConverter
    DATETIME_ATTR = viewLastModified createdAt publicationDate
    IN_FORMAT = %s$
    OUT_FORMAT = %Y-%m-%d
    PASSTHROUGH = NO
    REPAIR_INPUT = YES
    TEST_INPUT = 1611946240
    -> ATTRIBUTE_MANAGER_NG
    <REJECTED> -> VariableRetriever_7
VariableRetriever_7
    SCOPE = Global
    VALUE_ATTR = _timestamp
    VARNAME = _timestamp
    -> Error_Datetime (writer XLSXW_1)
Error_Datetime (writer XLSXW_1)
    attributes: publicationDate string(200), createdAt string(200), viewLastModified string(200), fme_rejection_code string(20), _timestamp string(200)

Bookmark: Attribute Manager
Note: Default_Attributes
ATTRIBUTE_MANAGER_NG
    IN_YAML_TEXT:
      # Default value fot tags
      tags{0}:
          action: attribute_not_null
          attr2set: default_domain_tag

      # Default value for description
      description:
          action: attribute_not_null
          attr2set: name
    -> ATTRIBUTE_MANAGER_NG_2
Note: Create Attributes
ATTRIBUTE_MANAGER_NG_2
    IN_YAML_TEXT:
      resource.id:
          action: attribute_overwrite
          attr2set: id

      resource.type:
          action: attribute_overwrite
          attr2set: assetType

      tags_copy:
          action: attribute_overwrite
          attr2set: tags

      spatialref{0}.projection_name:
          action: attribute_overwrite
          attr2set: default_projection_name

      spatialref{0}.projection_system:
          action: attribute_overwrite
          attr2set: default_reference_system

      spatialref{0}.projection_system_version:
          action: attribute_overwrite
          attr2set: default_projection_system_version

      sector:
          action: attribute_overwrite
          attr2set: metadata.custom_fields.Detailed Metadata.Department

      notes:
          action: attribute_overwrite
          attr2set: description

      title:
          action: attribute_overwrite
          attr2set: name

      record_publish_date:
          action: attribute_overwrite
          attr2set: publicationDate

      record_last_modified:
          action: attribute_overwrite
          attr2set: viewLastModified

      record_create_date:
          action: attribute_overwrite
          attr2set: createdAt

      updated_frequency:
          action: attribute_overwrite
          attr2set: metadata.custom_fields.Detailed Metadata.Frequency

      progress_code:
          action: attribute_overwrite
          attr2set: metadata.custom_fields.Detailed Metadata.Frequency

      range_collection_date:
          action: attribute_overwrite
          attr2set: metadata.custom_fields.Detailed Metadata.Time Period Coverage

      subject_tbs:
          action: attribute_overwrite
          attr2set: category

      topic_tbs:
          action: attribute_overwrite
          attr2set: category
    -> AttributeRemover_8
Note: Gestion des Tags
METADATA_VALUE_MAPPER_NG_6
    ATT_TO_MAP = tags{}.display_name
    CODE_REFRESH = NO
    ENGLISH_REFRESH = YES
    ERROR_NOT_MAPPED = NO
    FEATURE_TYPE = Keyword_NS
    FRENCH_REFRESH = NO
    IN_CSV_LOOKUP_TABLES_DIR = $(IN_CSV_LOOKUPTABLES_DIR)
    P-T_ABBR = $(P-T_ABBR)
    -> AttributeExposer_15
AttributeExposer_15
    ATTR_LIST = resource.id,range_collection_date
    -> UNIQUE_ID_CREATOR_2
UNIQUE_ID_CREATOR_2
    UNIQUE_ATT = @Value(resource.id)
    -> EXTRACT_COLLECTION_START_END_DATE

Bookmark: Replace Tags_copy{}
AttributeRemover_8
    LIST_ATTRS = tags{}
    -> PythonCaller_4
PythonCaller_4
    NEW_ATTRIBUTES = tags{}.display_name
    PYTHONSOURCE:
      import fme
      import fmeobjects
      # Template Function interface:
      # When using this function, make sure its name is set as the value of
      # the 'Class or Function to Process Features' transformer parameter
      def processFeature(feature):
          i=0
          for elem in feature.getAttribute('tags_copy{}'):
              feature.setAttribute('tags{%i}.display_name'%(i),elem)
              i+=1



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeRemover_9
AttributeRemover_9
    LIST_ATTRS = tags_copy{}
    -> METADATA_VALUE_MAPPER_NG_6 [DATA_INPUT]

Bookmark: Création de la liste des ressources pour les jeux de données
AttributeExposer_16
    ATTR_LIST = resource.id
    -> GEOPORTAL_WEBLINK_ADDER_NG_2
Note: GeoportalWeblink_NS
GEOPORTAL_WEBLINK_ADDER_NG_2
    FEATURE_TYPE = GeoportalWeblink_NS
    IN_CSV_LOOKUP_TABLES_DIR = $(IN_CSV_LOOKUPTABLES_DIR)
    P-T_ABBR = $(P-T_ABBR)
    URL_VALIDATION = $(URL_VALIDATION)
    WEBLINK_WILDCARD = @Value(resource.id)
    -> SOCRATA_ADDITIONAL_ACCESS_POINTS_RESOURCES_EXTRACTOR
Note: Extraction des ressources dans additional access points / Crée la liste additional_access_points_resources
SOCRATA_ADDITIONAL_ACCESS_POINTS_RESOURCES_EXTRACTOR
    -> SOCRATA_ATTACHEMENTS_EXTRACTOR
Note: Extraction des resources dans les attachements / Crée la liste attachement_resources
SOCRATA_ATTACHEMENTS_EXTRACTOR
    SBN_URL_ROOT = https://data.novascotia.ca
    URL_VALIDATION = $(URL_VALIDATION)
    -> SOCRATA_ADVANCED_VIEW_EXTRACTOR
Note: Extraction des ressources dans les vues avanacées / Crée la liste advancedview_resources
SOCRATA_ADVANCED_VIEW_EXTRACTOR
    -> SOCRATA_INSIDE_DB_EXTRACTOR_NG
SOCRATA_INSIDE_DB_EXTRACTOR_NG
    DOMAIN = https://data.novascotia.ca
    Field_datatype = NS_FieldType_NG
    Field_name = NS_GeoDataFieldName
    IN_CSV_LOOKUP_TABLES_DIR = $(IN_CSV_LOOKUPTABLES_DIR)
    LinkBuilderNonGeo = NS_LINKBUILDER_NONGEO
    P-T_ABBR = $(P-T_ABBR)
    URL_VALIDATION = $(URL_VALIDATION)
    linkbuilder_geo = NS_LINKBUILDER_GEO
    -> AttributeExposer_5
    Unknown_field_datatype -> socrata_unknown_field_type (writer XLSXW_1)
ListElementCounter
    CNT_ATTR = _element_count
    LIST_NAME = resources{}
    -> Tester_2
Tester_2
    BOOL_OP = OR
    COMPOSITE_TEST = 1
    TEST_CLAUSE = TEST @Value(_element_count) > 1
    TEST_MODE = TEST
    PASSED -> EMPTY_FORMAT_MAPPER_NG [DATA_INPUT]
EMPTY_FORMAT_MAPPER_NG
    CSV_FORMAT = format
    CSV_MIME_TYPE = Mime_type
    IN_CSV_LOOKUP_TABLES_DIR = $(IN_CSV_LOOKUPTABLES_DIR)
    P-T_ABBR = $(P-T_ABBR)
    URL_VALIDATION = $(URL_VALIDATION)
    DATA_OUTPUT -> GEO_NONE_GEO_SELECTOR_2
socrata_unknown_field_type (writer XLSXW_1)
    attributes: fieldName string(200), dataTypeName string(200), columns string(200)

Bookmark: Fusion des listes de resources dans une seule liste
AttributeExposer_5
    ATTR_LIST = resources{}.url
    -> ListCopier
ListCopier
    DEST_LIST = resources_copy
    SRC_LIST = resources{}
    -> AttributeRemover
AttributeRemover
    LIST_ATTRS = resources{}
    -> PythonCaller_3
PythonCaller_3
    NEW_ATTRIBUTES = resources{}.name resources{}.url resources{}.format resources{}.name_fr
    PYTHONSOURCE:
      import fme
      import fmeobjects
      logger = fmeobjects.FMELogFile()
      # Template Function interface:
      # When using this function, make sure its name is set as the value of
      # the 'Class or Function to Process Features' transformer parameter
      def processFeature(feature):
          list_list_name=[r'resources_copy',r'socrata_db_resources',r'advancedview_resources',r'additional_access_points_resources',r'attachement_resources']
          list_attr_name=[r'format',r'url',r'name',r'name_fr',r'spatial_type',r'fgp_publish']

          i=0





          for list_name in list_list_name:

              #Extracting number of resources
              list_url=feature.getAttribute('%s{}.url'%(list_name))
              if list_url:
                  #Looping in resources
                  for j in range(len(list_url)):
                      #Looping in attributes
                      for attr_name in list_attr_name:
                          feature.setAttribute('resources{%i}.%s'%(i,attr_name),feature.getAttribute('%s{%i}.%s'%(list_name,j,attr_name)))

                      #Changing index feature where new features
                      i=i+1
    PYTHONSYMBOL = processFeature
    -> ListDuplicateRemover_2
Note: Removing dupplicates on URL
ListDuplicateRemover_2
    SRC_LIST = resources{}.url
    -> AttributeExposer_7
AttributeExposer_7
    ATTR_LIST = resources_copy{},socrata_db_resources{},advancedview_resources{},additional_access_points_resources{},attachement_resources{}
    -> AttributeRemover_7
Note: Retrait des liste mergées
AttributeRemover_7
    LIST_ATTRS = additional_access_points_resources{} advancedview_resources{} attachement_resources{} resources_copy{} socrata_db_resources{}
    -> ListElementCounter

Bookmark: Filtrage geo / non-geo
Note: Sélection par format
GEO_NONE_GEO_SELECTOR_2
    CSV_FILE_NAME = GeoSpatialValidation
    CSV_PATH = $(IN_CSV_LOOKUPTABLES_DIR)
    CSV_PROVINCE = $(P-T_ABBR)
    YAML_DIRECTIVES:
      resources{}.format:
        domain: lookup_table_format
        spatial_type: overwrite
        not_found: log
        search_type: equals
    GEOSPATIAL -> Junction_2
    NONE_GEOSPATIAL -> GEO_NONE_GEO_SELECTOR_3
    LOG_ERROR -> VariableRetriever_13
Note: Sélection par fgp publish (peut être défini sur les features memes si le format n'est pas nécessairement géo)
GEO_NONE_GEO_SELECTOR_3
    CSV_FILE_NAME = GeoSpatialValidation
    CSV_PATH = $(IN_CSV_LOOKUPTABLES_DIR)
    CSV_PROVINCE = $(P-T_ABBR)
    YAML_DIRECTIVES:
      resources{}.fgp_publish:
       domain: [oui]
       spatial_type: no_overwrite
       not_found: no_log
       search_type: equals
    GEOSPATIAL -> Junction_2
    NONE_GEOSPATIAL -> GEO_NONE_GEO_SELECTOR_4
Note: Sélection par keywords
GEO_NONE_GEO_SELECTOR_4
    CSV_FILE_NAME = GeoSpatialValidation
    CSV_PATH = $(IN_CSV_LOOKUPTABLES_DIR)
    CSV_PROVINCE = $(P-T_ABBR)
    YAML_DIRECTIVES:
      tags{}.display_name:
       domain: [lidar,elevation,geoscientific,topography]
       spatial_type: no_overwrite
       not_found: no_log
       search_type: equals
    GEOSPATIAL -> Junction_2
    NONE_GEOSPATIAL -> AttributeExposer_21
Junction_2
    -> AttributeExposer_4 [off]
AttributeExposer_21
    ATTR_LIST = id,resource.id
    -> MANUAL_GEOSPATIAL_SETTER_NG [DATA_INPUT]
MANUAL_GEOSPATIAL_SETTER_NG
    FEATURE_TYPE = UnmappedGeoData_NS
    IN_CSV_LOOKUP_TABLES_DIR = $(IN_CSV_LOOKUPTABLES_DIR)
    P-T_ABBR = $(P-T_ABBR)
    GEOSPATIAL -> AttributeExposer_23
    NON-GEOSPATIAL -> AttributeRemover_5
    UNMAPPED_DATA -> VariableRetriever_14
AttributeRemover_5
    REMOVE_ATTRS = id_temp
    -> Tester_4
VariableRetriever_14
    SCOPE = Global
    VALUE_ATTR = _timestamp
    VARNAME = _timestamp
    -> unknow_geo_non_geo (writer XLSXW_1)
unknow_geo_non_geo (writer XLSXW_1)
    attributes: id string(200), notes string(200), title string(200), url string(200), _timestamp string(200)
VariableRetriever_13
    SCOPE = Global
    VALUE_ATTR = _timestamp
    VARNAME = _timestamp
    -> unknown_format (writer XLSXW_1)
unknown_format (writer XLSXW_1)
    attributes: format auto(20)

Bookmark: Adding spatial type manually
AttributeExposer_4
    ATTR_LIST = id,resource.id
    -> AttributeCreator_3
AttributeCreator_3
    ATTR_TABLE = SET_TO id_temp = @Value(id)
    -> AttributeCreator_4
AttributeCreator_4
    ATTR_TABLE = SET_TO id = @Value(resource.id)
    -> SPATIAL_TYPE_MAPPER_NG [DATA_INPUT]
Note: SpatialType_NS
SPATIAL_TYPE_MAPPER_NG
    FEATURE_TYPE = SpatialType_NS
    IN_CSV_LOOKUP_TABLES_DIR = $(IN_CSV_LOOKUPTABLES_DIR)
    P-T_ABBR = $(P-T_ABBR)
    DATA_OUTPUT_FAILED -> VariableRetriever
    DATA_OUTPUT_PASSED -> AttributeExposer_23
VariableRetriever
    SCOPE = Global
    VALUE_ATTR = _timestamp
    VARNAME = _timestamp
    -> Spatial_Type_Mapper_Failed (writer XLSXW_1)
Spatial_Type_Mapper_Failed (writer XLSXW_1)
    attributes: id string(20), title string(80), url string(80)
AttributeExposer_23
    ATTR_LIST = id_temp
    -> Tester_3

Bookmark: Activate Geo and Sample or full content
Note: GEO activated?
Tester_3
    BOOL_OP = OR
    COMPOSITE_TEST = 1
    TEST_CLAUSE = TEST @UpperCase($(ACTIVATE_GEO)) = YES
    TEST_MODE = TEST
    PASSED -> TestFilter
TestFilter
    DEFAULT_VALUE = SAMPLES FEATURES
    TEST_LIST = "BOOL_OP,OR,COMPOSITE_TEST,""""""1"""""",TEST_CLAUSE,TEST $(SAMPLE_SIZE) = 0",ALL FEATURES
    ALL FEATURES -> Junction_5
    SAMPLES FEATURES -> Sampler_3
Sampler_3
    RATE = $(SAMPLE_SIZE)
    SAMPLE_MODE = No
    SAMPLE_TYPE_LONG = First N Features
    SAMPLED -> Junction_5
Junction_5
    -> Socrata_BoundingBoxExtractor [feature_input]

Bookmark: Metadata Value Mapping - GEO
Note: Topic
METADATA_VALUE_MAPPER_NG
    ATT_TO_MAP = category
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_2 [DATA_INPUT]
Note: Role
METADATA_VALUE_MAPPER_NG_2
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_3 [DATA_INPUT]
Note: Update
METADATA_VALUE_MAPPER_NG_3
    ATT_TO_MAP = updated_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: Progress
METADATA_VALUE_MAPPER_NG_4
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: SpatialRepresentation
METADATA_VALUE_MAPPER_NG_5
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> VariableRetriever_11
    DATA_OUTPUT -> AttributeRemover_6
Note: Removing error list
AttributeRemover_6
    LIST_ATTRS = mapping_errors{}
    -> RESOURCE_NAME_UNDERSCORE_REMOVER
VariableRetriever_11
    SCOPE = Global
    VALUE_ATTR = _timestamp
    VARNAME = _timestamp
    -> GEO_ATTRIBUTE_MAPPING_ERRORS (writer XLSXW_1)
GEO_ATTRIBUTE_MAPPING_ERRORS (writer XLSXW_1)
    attributes: error string(200), id string(200), _element_index string(200), _timestamp string(200)

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    URL_VALIDATION = $(URL_VALIDATION)
    -> WMS_REST_LANGUAGE_FORMATTER
    FAULTY_URL_OUTPUT -> VariableRetriever_2
VariableRetriever_2
    SCOPE = Global
    VALUE_ATTR = _timestamp
    VARNAME = _timestamp
    -> MAP_SERVICE_URL_ERRORMAP (writer XLSXW_1)
MAP_SERVICE_URL_ERRORMAP (writer XLSXW_1)
    attributes: id string(200), url string(200), format string(200), _url_failure_message string(200), _timestamp string(200)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> PYCSW_URL_MAPPER_NG

Bookmark: New Bookmark
Note: PyCSW_config
PYCSW_URL_MAPPER_NG
    FEATURE_TYPE = PyCSW_config
    FORCED_PYCSW_URL = $(FORCED_PYCSW_URL)
    IN_CSV_LOOKUP_TABLES_DIR = $(IN_CSV_LOOKUPTABLES_DIR)
    P-T_ABBR = $(P-T_ABBR)
    -> AttributeExposer_2
AttributeExposer_2
    ATTR_LIST = search_criteria_pycsw,csw_url
    -> METADATA_DELTA_FINDER_NG
Note: Searches existing PyCSW for new, updated or obsolete data
METADATA_DELTA_FINDER_NG
    ABSTRACT_ATT_NEW = notes
    ABSTRACT_ATT_REF = MD_Metadata.identificationInfo.MD_DataIdentification.abstract.CharacterString
    CSW_FILTER = NO
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> StatisticsCalculator_Summary_3
    Update -> Junction_3
    Insert -> Junction_3
    Delete -> DELETED_RECORDS_NONE_GEO (writer XLSXW_1)
Note: Log statistics
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
Junction_3
    -> AttributeExposer
Note: Log deleted features
DELETED_RECORDS_NONE_GEO (writer XLSXW_1)
    attributes: id auto(20)
AttributeCreator_7
    ATTR_TABLE = SET_TO _typedataset = NONGEO
    -> AttributeExposer
Note: Exposes PyCSW_Transaction attribute
AttributeExposer
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> Tester
    Update -> Junction
    Insert -> AttributeExposer_13
    Delete -> AttributeKeeper
Terminator
    MESSAGE = ERROR: Unknown _event value from Metadata_Delta
Note: Selects items with no change for publishing, overwriting all existing data
Tester
    BOOL_OP = OR
    COMPOSITE_TEST = 1
    TEST_CLAUSE = TEST @UpperCase(NO) = YES
    TEST_MODE = TEST
    PASSED -> AttributeCreator
    FAILED -> AttributeExposer_10
AttributeExposer_10
    ATTR_LIST = id
    -> StatisticsCalculator
Note: Reset to update
AttributeCreator
    ATTR_TABLE = SET_TO PyCSW_Transaction = Update
    -> Junction
Junction
    -> Junction_4
Note: Retains ID for list of deleted items
AttributeKeeper
    KEEP_ATTRS = id
    -> VariableRetriever_9
VariableRetriever_9
    SCOPE = Global
    VALUE_ATTR = _timestamp
    VARNAME = _timestamp
    -> AttributeExposer_12
AttributeExposer_12
    ATTR_LIST = id
    -> DELETEDRECORDS (writer XLSXW_1)
DELETEDRECORDS (writer XLSXW_1)
    attributes: _timestamp string(200), id string(200)
AttributeExposer_13
    ATTR_LIST = resource.id,title
    -> Junction_4
Creator_2
    GEOMTYPE = Geometry Object
    NUM = 1
    CREATED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO

Bookmark: Activate None Geo and Sample or fulle content
Note: NONE GEO activated?
Tester_4
    BOOL_OP = OR
    COMPOSITE_TEST = 1
    TEST_CLAUSE = TEST @UpperCase($(ACTIVATE_NON_GEO)) = YES
    TEST_MODE = TEST
    PASSED -> TestFilter_3
TestFilter_3
    DEFAULT_VALUE = SAMPLES FEATURES
    TEST_LIST = "BOOL_OP,OR,COMPOSITE_TEST,""""""1"""""",TEST_CLAUSE,TEST $(SAMPLE_SIZE) = 0",ALL FEATURES
    ALL FEATURES -> Junction_7
    SAMPLES FEATURES -> Sampler_4
Sampler_4
    RATE = $(SAMPLE_SIZE)
    SAMPLE_MODE = No
    SAMPLE_TYPE_LONG = First N Features
    SAMPLED -> Junction_7
Junction_7
    -> METADATA_VALUE_MAPPER_NG_7 [DATA_INPUT]

Bookmark: Metadata Value Mapping - NONGEO
Note: UpdateFrequency_TBS
METADATA_VALUE_MAPPER_NG_7
    ATT_TO_MAP = updated_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUPTABLES_DIR)
    P-T_ABBR = $(P-T_ABBR)
    -> METADATA_FORMAT_MAPPER_NG_2 [DATA_INPUT]
Note: Format_TBS
METADATA_FORMAT_MAPPER_NG_2
    ATT_TO_MAP = resources{}.format
    ERROR_NOT_MAPPED = YES
    FEATURE_TYPE = Format_TBS
    IN_CSV_LOOKUP_TABLES_DIR = $(IN_CSV_LOOKUPTABLES_DIR)
    P-T_ABBR = $(P-T_ABBR)
    REAL_VALUE_REFRESH = YES
    RES_TYPE_EN_REFRESH = NO
    RES_TYPE_FR_REFRESH = NO
    -> METADATA_VALUE_MAPPER_NG_9 [DATA_INPUT]
Note: Subject_TBS
METADATA_VALUE_MAPPER_NG_9
    ATT_TO_MAP = subject_tbs
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUPTABLES_DIR)
    P-T_ABBR = $(P-T_ABBR)
    -> METADATA_VALUE_MAPPER_NG_10 [DATA_INPUT]
Note: Topic_TBS
METADATA_VALUE_MAPPER_NG_10
    ATT_TO_MAP = topic_tbs
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUPTABLES_DIR)
    P-T_ABBR = $(P-T_ABBR)
    -> AttributeExposer_19
AttributeExposer_19
    ATTR_LIST = org_name
    -> AttributeCreator_6
AttributeCreator_6
    ATTR_TABLE = SET_TO organization_name = @Value(org_name)
    -> METADATA_VALUE_MAPPER_ERROR_MANAGER_2
METADATA_VALUE_MAPPER_ERROR_MANAGER_2
    ERROR_OUTPUT -> VariableRetriever_3
    DATA_OUTPUT -> METADATA_DELTA_FINDER_NG_2
VariableRetriever_3
    SCOPE = Global
    VALUE_ATTR = _timestamp
    VARNAME = _timestamp
    -> NON_GEO_ATTRIBUTE_MAPPING_ERRORS (writer XLSXW_1)
NON_GEO_ATTRIBUTE_MAPPING_ERRORS (writer XLSXW_1)
    attributes: error string(200), id string(200), _element_index string(200), _timestamp string(200)
METADATA_DELTA_FINDER_NG_2
    ABSTRACT_ATT_NEW = notes
    ABSTRACT_ATT_REF = notes_translated.en
    DATESTAMP_ATT_NEW = record_last_modified
    DATESTAMP_ATT_REF = federated_date_modified
    ID_ATT_NEW = id
    ID_ATT_REF = id
    LOCAL_SOURCE = $(LOCAL_SOURCE_METADATA_DELTA_FINDER)
    LOCAL_SOURCE_DIR = $(OUT_JSON_LOCAL_DIR)
    LOCAL_SOURCE_FORMAT = JSON
    METADATA_OVERWRITE = $(METADATA_OVERWRITE)
    RES_NAME_ATT_NEW = resources{}.name
    RES_NAME_ATT_REF = resources{}.name_translated.en
    RES_URL_ATT_NEW = resources{}.url
    RES_URL_ATT_REF = resources{}.url
    TITLE_ATT_NEW = title
    TITLE_ATT_REF = title_translated.en
    Statistics -> StatisticsCalculator_Summary_2
    Update -> Junction_6
    Insert -> Junction_6
    Delete -> DELETED_RECORDS_NONE_GEO00 (writer XLSXW_1)
Note: Log statistics
StatisticsCalculator_Summary_2: Logger
    LOG_FEATURE = NONE
    MAXFEATS = 20
    MESSAGE:
      ************************
      **** NoneGeo Features: Unchanged Report ****
      ************************

      @Value(_real_count) features were unchanged

      ************************
      ************************
      ************************
    SEVERITY = INFO
Junction_6
    -> AttributeCreator_7

Bookmark: AWS Translation
Note: English to french / notes, / title, / tags_en / resources name
AWS_TRANSLATE_2
    ACTIVATE_TRANSLATION = $(ACTIVATE_TRANSLATION)
    ATTR_2_TRANSLATE = notes,title,sector
    ATTR_LIST_2_TRANSLATE = tags{}.display_name,resources{}.name
    MODE = English-->French
    -> AttributeExposer_20
    TRANSLATION_PROBLEM -> VariableRetriever_5
AttributeExposer_20
    ATTR_LIST = _typedataset
    -> Tester_5
Tester_5
    BOOL_OP = OR
    COMPOSITE_TEST = 1
    TEST_CLAUSE = TEST @Value(_typedataset) = NONGEO
    TEST_MODE = TEST
    PASSED -> AttributeExposer_17
    FAILED -> AttributeExposer_6
VariableRetriever_5
    SCOPE = Global
    VALUE_ATTR = _timestamp
    VARNAME = _timestamp
    -> Translation_errors (writer XLSXW_1)
Translation_errors (writer XLSXW_1)
    attributes: id string(20), _timestamp string(20)

Bookmark: Rebuilding tags list
AttributeExposer_6
    ATTR_LIST = tags{}
    -> ListElementCounter_2
ListElementCounter_2
    CNT_ATTR = _nb_tags
    LIST_NAME = tags{}
    -> PythonCaller_2
PythonCaller_2
    NEW_ATTRIBUTES = tags{}.display_name_lower tags{}.display_name_fr_lower
    PYTHONSOURCE:
      import fme
      import fmeobjects
      # Template Function interface:
      # When using this function, make sure its name is set as the value of
      # the 'Class or Function to Process Features' transformer parameter
      def processFeature(feature):
          i=0

          for j in range(int(feature.getAttribute('_nb_tags'))):
              feature.setAttribute('tags{%i}.display_name_lower'%(i),feature.getAttribute('tags{%i}.display_name'%(j)).lower())
              feature.setAttribute('tags{%i}.display_name_fr_lower'%(i),feature.getAttribute('tags{%i}.display_name_fr'%(j)).lower())
              i=i+1
    PYTHONSYMBOL = processFeature
    -> XML_PUBLISHER_NG

Bookmark: XML CREATION AND WRITING
Note: Config_NS
XML_PUBLISHER_NG
    FEATURE_TYPE = Config_NS
    IN_CSV_LOOKUP_TABLES_DIR = $(IN_CSV_LOOKUPTABLES_DIR)
    LOCAL_WRITER = $(LOCAL_WRITER)
    P-T_ABBR = $(P-T_ABBR)
    TEMPLATE_GMD_CITEDRESPONSIBLEPARTY = $(IN_GMD_XML_TEMPLATE_DIR)//GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> text_line (writer TEXTLINE_2)
    UPDATE_FAILED -> VariableRetriever_12

Bookmark: JSON CREATION AND WRITING
AttributeExposer_17
    ATTR_LIST = tags{}.display_name,tags{}.display_name_fr
    -> JSON_PUBLISHER_NG
Note: NS_JSON_CONFIG
JSON_PUBLISHER_NG
    FEATURE_TYPE = NS_JSON_CONFIG
    IN_CSV_LOOKUP_TABLES_DIR = $(IN_CSV_LOOKUPTABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name
    Keywords_FR = tags{}.display_name_fr
    P-T_ABBR = $(P-T_ABBR)
    Subject_LIST = subject_tbs
    Topic_LIST = topic_tbs
    OUTPUT_LOCAL -> AttributeExposer_18
AttributeExposer_18
    ATTR_LIST = json_file,id,sector
    -> AttributeCreator_8
AttributeCreator_8
    ATTR_TABLE = SET_TO text_line_data = @Value(json_file)
    -> text_line (writer TEXTLINE_4)
text_line (writer TEXTLINE_4)
    attributes: text_line_data buffer

FME custom transformer Catalogue Reader
Transformer permettant d'obtenir les enregistrements présents dans les catalogues staging et prod (internes et externes).
Il est possible de faire un tri des jeux de données par provinces ou de spécifier un identifiant unique ou une liste d'identifiant à rechercher.

Parameters:
- LOOKUP_LISTBOX =
- SOURCE_URL =
- CUSTOM_URL =
- CKAN_FILTER = fq=collection:fgp   # fq=collection:fgp CKAN_FILTER
- CUSTOM_CSW_SCHEMA =
- CUSTOM_CSW_VERSION =
- CUSTOM_URL_CSW_TYPENAMES =
- CUSTOM_CSW_LIST_NAME = DefaultNoList{}
- IDENTIFIANT =
- CUSTOM_URL_BY_ID_ATT_NAME =
- CSW_ANYTEXT_FILTER =

AttributeFilter
    ATTR_NAME = _type_requete
    ATTR_VALUES = CKAN-AllRecords,CSW-AllRecords,CKAN-ByID,CSW-ByID,<Empty>,<Missing>,<Null>,<Unfiltered>
    CKAN-AllRecords -> Tester_2
    CSW-AllRecords -> Tester_13
    CKAN-ByID -> HTTPCaller_4
    CSW-ByID -> HTTPCaller_2
    <EMPTY> -> Terminator_5
    <MISSING> -> Terminator_5
    <NULL> -> Terminator_5
    <UNFILTERED> -> Terminator_5
Terminator_10
    MESSAGE = Translation Terminated
BulkAttributeRenamer
    ATTRCHOICE = All Attributes
    CASE_DISP = NO
    MODE_CHOICE = RENAME
    PATTERN_ACTION_DISP = STRINGREPLACE
    REPLACE_PATTERN = temp_name_
    REPLACE_STR = @Value(_list_name)
    -> AttributeExploder
Terminator_5
    MESSAGE = Translation Terminated
AttributeRemover
    REMOVE_ATTRS = _response_body,root_url,_http_status_code,ErreurUUID,_id,_type_requete
    -> Résultats (output)
Résultats (output)
Identifiant_Non_trouvé: AttributeCreator
    ATTR_TABLE = SET_TO Statut = Métadonnée non trouvée
    -> AttributeRemover_2
AttributeRemover_2
    LIST_ATTRS = MD_Metadata{}
    REMOVE_ATTRS = _id,_http_status_code,fme_rejection_code,ErreurUUID,Statut
    -> Logger_2
Logger_2
    LOG_FEATURE = LOG_ONLY
    MAXCOORDS = 20
    MAXFEATS = 1000
    MESSAGE = Problème au niveau de la liste d'Identifiants (UUID invalide, présence d'espace, etc)  ou Problème d'accessibilité de l'Environnement sélectionné (serveur Down, UUID non présent dans l'environnement choisi)
    SEVERITY = WARN
    LOGGED -> MetadonnéesNonTrouvées (output)
MetadonnéesNonTrouvées (output)

Bookmark: Préparation du call HTTP
Input (input)
    -> AttributeCreator_2
Note: Transfert des paramètres en attributs
AttributeCreator_2
    ATTR_TABLE:
      SET_TO _id = $(IDENTIFIANT)
      SET_TO root_url = $(SOURCE_URL)
    -> Tester_8
Note: CUSTOM URL
Tester_8
    BOOL_OP = OR
    COMPOSITE_TEST = 1
    TEST_CLAUSE = TEST $(CUSTOM_URL) != ""
    TEST_MODE = TEST
    PASSED -> AttributeCreator_8
    FAILED -> Tester_7
Note: On écrase la valeur
AttributeCreator_8
    ATTR_TABLE = SET_TO root_url = $(CUSTOM_URL)
    -> Tester_7
Note: CKAN ou CSW
Tester_7
    BOOL_OP = OR
    COMPOSITE_TEST = 1
    TEST_CLAUSE = CASE_INSENSITIVE_TEST @LowerCase(@Value(root_url)) CONTAINS csw
    TEST_MODE = CASE_INSENSITIVE_TEST
    PASSED -> AttributeCreator_9
    FAILED -> AttributeCreator_10
AttributeCreator_9
    ATTR_TABLE = SET_TO _type_requete = CSW
    -> Tester_3
AttributeCreator_10
    ATTR_TABLE = SET_TO _type_requete = CKAN
    -> Tester_3
Note: All records / By record
Tester_3
    BOOL_OP = OR
    COMPOSITE_TEST = 1
    TEST_CLAUSE = TEST _id NOT_ATTRIBUTE_HAS_A_VALUE ""
    TEST_MODE = TEST
    PASSED -> AttributeCreator_12
    FAILED -> Logger
Logger
    LOG_FEATURE = LOG_ONLY
    MAXCOORDS = 20
    MAXFEATS = 20
    MESSAGE = La présence d'un attribut "Identifiant" bypass le tri par attribut "provider".
    SEVERITY = WARN
    LOGGED -> PythonCaller
AttributeCreator_11
    ATTR_TABLE = SET_TO _type_requete = @Value(_type_requete)-ByID
    -> Tester
UUID_invalide (output)
AttributeCreator_12
    ATTR_TABLE = SET_TO _type_requete = @Value(_type_requete)-AllRecords
    -> Tester

Bookmark: Validation UUID
PythonCaller
    NEW_ATTRIBUTES = ErreurUUID
    PYTHONSOURCE:
      import fme
      import fmeobjects
      from uuid import UUID
      # Template Function interface:
      # When using this function, make sure its name is set as the value of
      # the 'Class or Function to Process Features' transformer parameter
      def processFeature(feature):
          if not validate_uuid4(feature.getAttribute('_id')):
              feature.setAttribute("ErreurUUID","OUI")

      def validate_uuid4(uuid):

          """
          Validate that a UUID string is in
          fact a valid uuid4.
          Happily, the uuid module does the actual
          checking for us.
          It is vital that the 'version' kwarg be passed
          to the UUID() call, otherwise any 32-character
          hex string is considered valid.
          """

          try:
              val = UUID(uuid, version=4)
              return True
          except ValueError:

              return False
    PYTHONSYMBOL = processFeature
    -> Tester_4
Tester_4
    BOOL_OP = OR
    COMPOSITE_TEST = 1
    TEST_CLAUSE = TEST @Value(ErreurUUID) = OUI
    TEST_MODE = TEST
    PASSED -> UUID_invalide (output)
    FAILED -> AttributeCreator_11

Bookmark: CUSTOM CSW or FGP stuff
Tester
    BOOL_OP = OR
    COMPOSITE_TEST = 1
    TEST_CLAUSE = CASE_INSENSITIVE_TEST @LowerCase(@Value(root_url)) CONTAINS csw
    TEST_MODE = CASE_INSENSITIVE_TEST
    PASSED -> Tester_5
    FAILED -> AttributeFilter
Note: Custom URL Defined
Tester_5
    BOOL_OP = OR
    COMPOSITE_TEST = 1
    TEST_CLAUSE = TEST $(CUSTOM_URL) != ""
    TEST_MODE = TEST
    PASSED -> Tester_9
    FAILED -> AttributeCreator_5
Tester_9
    BOOL_OP = COMPOSITE
    COMPOSITE_TEST = 1 AND 2
    TEST_CLAUSE:
      TEST $(CUSTOM_CSW_VERSION) != ""
      TEST $(CUSTOM_CSW_SCHEMA) != ""
    TEST_MODE = TEST
    PASSED -> AttributeCreator_13
    FAILED -> Terminator_9
AttributeCreator_13
    ATTR_TABLE:
      SET_TO csw_version = $(CUSTOM_CSW_VERSION)
      SET_TO csw_schema = $(CUSTOM_CSW_SCHEMA)
    -> Tester_12
Tester_12
    BOOL_OP = OR
    COMPOSITE_TEST = 1
    TEST_CLAUSE = TEST $(CUSTOM_URL_CSW_TYPENAMES) != ""
    TEST_MODE = TEST
    PASSED -> AttributeCreator_15
    FAILED -> AttributeFilter
AttributeCreator_15
    ATTR_TABLE = SET_TO csw_typenames = &typeNames=$(CUSTOM_URL_CSW_TYPENAMES)
    -> AttributeFilter
Terminator_9
    MESSAGE = Translation Terminated
AttributeCreator_5
    ATTR_TABLE:
      SET_TO csw_version = 2.0.2
      SET_TO csw_schema = http://www.isotc211.org/2005/gmd
      SET_TO csw_typenames = &typeNames=gmd:MD_Metadata
      SET_TO csw_filter = &constraintLanguage=FILTER
    -> AttributeFilter

Bookmark: Adding filter for OPenMaps
Note: OPenMaps ou autreCKAN
Tester_2
    BOOL_OP = OR
    COMPOSITE_TEST = 1
    TEST_CLAUSE = TEST $(CKAN_FILTER) != ""
    TEST_MODE = TEST
    PASSED -> AttributeCreator_4
    FAILED -> HTTPCaller_5
AttributeCreator_4
    ATTR_TABLE = SET_TO _OpenMapsFilter = &$(CKAN_FILTER)
    -> HTTPCaller_5

Bookmark: Lecture CKAN_OpenMaps
Note: Obtenir le nombre feature dans CKAN dans la collection FGP
HTTPCaller_5
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)/package_search?start=0&rows=1@Value(_OpenMapsFilter)
    TRANSFER_TIMEOUT_LENGTH = 90
    USE_COOKIES = No
    VERIFY_SSL_CERTIFICATES = No
    -> JSONFlattener_2
    <REJECTED> -> Terminator_6
JSONFlattener_2
    ERROR_LIST_ATTR = _json_error
    JSON_DOCUMENT = @Value(_response_body)
    READ_FROM_FILE = NO
    RECURSIVE = Yes
    -> AttributeExposer_3
    <REJECTED> -> Terminator_7
AttributeExposer_3
    ATTR_LIST = result.count
    -> AttributeCreator_6
AttributeCreator_6
    ATTR_TABLE = SET_TO nb_paquet = @Evaluate(@ceil(@Value(result.count)/10))
    -> Cloner_2
Cloner_2
    COPIES = @Value(nb_paquet)
    COPYATT = _copynum
    COPY -> AttributeCreator_7
AttributeCreator_7
    ATTR_TABLE = SET_TO start_index = @Evaluate(@Value(_copynum)*10)
    -> AttributeKeeper_2
AttributeKeeper_2
    KEEP_ATTRS = _OpenMapsFilter,start_index,root_url
    -> HTTPCaller_7
Note: Lecture CKAN
HTTPCaller_7
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)/package_search?start=@Value(start_index)&rows=10@Value(_OpenMapsFilter)
    TRANSFER_TIMEOUT_LENGTH = 90
    USE_COOKIES = No
    VERIFY_SSL_CERTIFICATES = No
    -> JSONFlattener_3
    <REJECTED> -> Terminator_8
JSONFlattener_3
    ERROR_LIST_ATTR = _json_error
    JSON_DOCUMENT = @Value(_response_body)
    READ_FROM_FILE = NO
    RECURSIVE = Yes
    -> AttributeExposer_4
AttributeExposer_4
    ATTR_LIST = result.results{}
    -> ListExploder_4
ListExploder_4
    ATTR_ACCUM_MODE = Merge List Attributes
    ATTR_CONFLICT_RES = Use List Attribute Values
    INDEX_ATTR = _element_index
    LIST_ATTR = result.results{}
    ELEMENTS -> AttributeExploder
    <REJECTED> -> Terminator_10
Terminator_8
    MESSAGE = Translation Terminated
Terminator_7
    MESSAGE = Translation Terminated
Terminator_6
    MESSAGE = Translation Terminated

Bookmark: Gestion du nombre d'entités à traiter pour le bon fonctionnement du processus. lot de 10 entrées à la fois.
Tester_13
    BOOL_OP = OR
    COMPOSITE_TEST = 1
    TEST_CLAUSE = TEST $(CSW_ANYTEXT_FILTER) = ""
    TEST_MODE = TEST
    PASSED -> HTTPCaller
    FAILED -> AttributeCreator_17
AttributeCreator_17
    ATTR_TABLE = SET_TO _temp_csw_search_criteria = $(CSW_ANYTEXT_FILTER)
    -> TextEncoder
TextEncoder
    DEST_ATTR = _temp_csw_search_criteria
    ENCODING_TYPE = URL_ENCODE
    STRING_TO_ENCODE = @Value(_temp_csw_search_criteria)
    -> AttributeCreator_16
AttributeCreator_16
    ATTR_TABLE = SET_TO csw_search_criteria = &constraintlanguage=CQL_TEXT&constraint=apiso%3AAnyText%20like%20@Value(_temp_csw_search_criteria)
    -> HTTPCaller
Note: Identifier le nombre de fichiers dans le noeud CSW
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)request=GetRecords&service=CSW&version=@Value(csw_version)&elementSetName=full@Value(csw_typenames)@Value(csw_filter)@Value(csw_search_criteria)
    TRANSFER_TIMEOUT_LENGTH = 90
    USE_COOKIES = No
    VERIFY_SSL_CERTIFICATES = No
    -> XMLFlattener_2
    <REJECTED> -> Terminator_3
Note: Extraire l'information
XMLFlattener_2
    ATTRIBUTE_XML = _response_body
    EMBEDDED_EXPRESSIONS = SearchResults
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = SearchResults.numberOfRecordsMatched
    XML_SOURCE_TYPE = Attribute with XML document
    -> AttributeCreator
    <REJECTED> -> Terminator
Note: Calculer le nombre de paquets pour la lecture
AttributeCreator
    ATTR_TABLE:
      SET_TO NbPaquets = @Evaluate(@ceil(@Value(SearchResults.numberOfRecordsMatched)/10))
      SET_TO NbRecords = @Value(SearchResults.numberOfRecordsMatched)
    -> Cloner
Cloner
    COPIES = @Value(NbPaquets)
    COPYATT = _copynum
    COPY -> AttributeCreator_22
AttributeCreator_22
    ATTR_TABLE = SET_TO debut = @Evaluate(1+@Value(_copynum)*10)
    -> AttributeKeeper
AttributeKeeper
    KEEP_ATTRS = csw_schema,csw_search_criteria,csw_version,root_url,NbRecords,debut,csw_filter,csw_typenames
    -> HTTPCaller_3
Note: Lecutre par paquet de 10
HTTPCaller_3
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)request=GetRecords&service=CSW&version=@Value(csw_version)&elementSetName=full&ElementSetName=full&resultType=results&startPosition=@Value(debut)&maxRecords=10&outputSchema=@Value(csw_schema)@Value(csw_filter)@Value(csw_typenames)@Value(csw_search_criteria)
    TRANSFER_TIMEOUT_LENGTH = 90
    USE_COOKIES = No
    VERIFY_SSL_CERTIFICATES = No
    -> XMLFlattener
    <REJECTED> -> Terminator_4
XMLFlattener
    ATTRIBUTE_XML = _response_body
    EMBEDDED_EXPRESSIONS = SearchResults
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> Tester_10
Note: Custom URL Defined
Tester_10
    BOOL_OP = OR
    COMPOSITE_TEST = 1
    TEST_CLAUSE = TEST $(CUSTOM_URL) != ""
    TEST_MODE = TEST
    PASSED -> ListExploder_3
    FAILED -> AttributeExposer
Note: Créer une entité par métadonnées
ListExploder_3
    ATTR_ACCUM_MODE = Prefix List Attributes
    INCOMING_PREFIX = temp_name_.
    INDEX_ATTR = _element_index
    LIST_ATTR = $(CUSTOM_CSW_LIST_NAME)
    ELEMENTS -> AttributeCreator_14
    <REJECTED> -> AttributeCreator_14
AttributeCreator_14
    ATTR_TABLE = SET_TO _list_name = $(CUSTOM_CSW_LIST_NAME)
    -> StringReplacer
StringReplacer
    CASE = NO
    FIND_TEXT = {}
    NO_MATCH = _FME_NO_OP_
    REGEXP = NO
    SRC_ATTRS = _list_name
    -> BulkAttributeRenamer
AttributeExposer
    ATTR_LIST = MD_Metadata{}
    -> ListExploder_2
Note: Créer une entité par métadonnées
ListExploder_2
    ATTR_ACCUM_MODE = Prefix List Attributes
    INCOMING_PREFIX = MD_Metadata.
    INDEX_ATTR = _element_index
    LIST_ATTR = MD_Metadata{}
    ELEMENTS -> AttributeExploder
    <REJECTED> -> AttributeExploder
Terminator_4
    MESSAGE = Translation Terminated
Terminator
    MESSAGE = Translation Terminated
Terminator_3
    MESSAGE = Translation Terminated

Bookmark: Extraction des données selon la licence. Le modèle de données n'importe pas
AttributeExploder
    ATTR_NAME_LABEL = _attr_name
    ATTR_VALUE_LABEL = _attr_value
    EXPLODING_TYPE = List
    KEEP_ATTRIBUTES = Yes
    KEEP_GEOMETRY = No
    LIST_NAME = _attr_list
    -> AttributeCreator_3
Note: Transfert en attributs des provider à identifier
AttributeCreator_3
    ATTR_TABLE = SET_TO list_provider = $(FILTER_PROVIDER)
    -> AttributeTrimmer
AttributeTrimmer
    SRC_ATTRS = list_provider
    TRIM_CHARS = "
    TRIM_TO_NONE = Yes
    TRIM_TYPE = Both
    -> AttributeSplitter
AttributeSplitter
    ATTR_NAME = list_provider
    DELIMITER = " "
    DROP_EMPTY_PARTS = No
    LIST_NAME = _listprovider
    TRIM_OPTION = Both
    -> ListConcatenator
ListConcatenator
    DROP_EMPTY_PARTS = No
    LIST_ATTR = _attr_list{}._attr_value
    SEP = ,
    VAL_ATTR = _concatenated
    -> AttributeRemover_4
AttributeRemover_4
    LIST_ATTRS = _attr_list{} _attr_list{}._attr_name _attr_list{}._attr_value
    -> PythonCaller_2
Note: Recherche dans la liste de valeur, les licences attendues
PythonCaller_2
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              list_provider=feature.getAttribute('_listprovider{}')
              list_text=feature.getAttribute('_concatenated')

              for provider in list_provider:
                  if provider in list_text:
                      self.pyoutput(feature)
                      break

          def close(self):
              pass
    PYTHONSYMBOL = FeatureProcessor
    -> AttributeRemover_3
AttributeRemover_3
    LIST_ATTRS = _listprovider{}
    REMOVE_ATTRS = debut,NbRecords,_response_body,list_provider,_concatenated,fme_rejection_code,root_url,_http_status_code,start_index,_element_index
    -> BulkAttributeRemover
BulkAttributeRemover
    ATTR_EXP = SearchResults^
    -> Résultats (output)

Bookmark: Lecture dans CKAN par ID
Note: CKAN
HTTPCaller_4
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)/package_show?id=@Value(_id)
    TRANSFER_TIMEOUT_LENGTH = 90
    USE_COOKIES = No
    VERIFY_SSL_CERTIFICATES = No
    -> JSONFlattener
    <REJECTED> -> Identifiant_Non_trouvé
JSONFlattener
    ERROR_LIST_ATTR = _json_error
    JSON_DOCUMENT = @Value(_response_body)
    READ_FROM_FILE = NO
    RECURSIVE = Yes
    -> AttributeExposer_2
    <REJECTED> -> Identifiant_Non_trouvé
AttributeExposer_2
    ATTR_LIST = result.file_id
    -> AttributeRemover

Bookmark: Requête CSW - GetRecordByID
Note: CSW
HTTPCaller_2
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)request=GetRecordById&service=CSW&version=@Value(csw_version)&elementSetName=full&id=@Value(_id)&outputSchema=@Value(csw_schema)@Value(csw_typenames)@Value(csw_filter)
    TRANSFER_TIMEOUT_LENGTH = 90
    USE_COOKIES = No
    VERIFY_SSL_CERTIFICATES = No
    -> Tester_6
    <REJECTED> -> Logger_2
Note: Custom URL Defined
Tester_6
    BOOL_OP = OR
    COMPOSITE_TEST = 1
    TEST_CLAUSE = TEST $(CUSTOM_URL) != ""
    TEST_MODE = TEST
    PASSED -> Tester_11
    FAILED -> XMLFlattener_3
Tester_11
    BOOL_OP = OR
    COMPOSITE_TEST = 1
    TEST_CLAUSE = TEST $(CUSTOM_URL_BY_ID_ATT_NAME) != ""
    TEST_MODE = TEST
    PASSED -> XMLFlattener_4
    FAILED -> Terminator_2
XMLFlattener_4
    ATTRIBUTE_XML = _response_body
    EMBEDDED_EXPRESSIONS = $(CUSTOM_URL_BY_ID_ATT_NAME)
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> AttributeRemover
    <REJECTED> -> Identifiant_Non_trouvé
Terminator_2
    MESSAGE = Translation Terminated
XMLFlattener_3
    ATTRIBUTE_XML = _response_body
    EMBEDDED_EXPRESSIONS = GetRecordByIdResponse
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> AttributeRemover
    <REJECTED> -> Identifiant_Non_trouvé

FME custom transformer ListSlicer_2
Replaces an existing list with a list containing elements of the slicing range which is determined by the starting index and the number of elements.
If the source list was a structured one like "_list{}.foo", "_list{}.bar", all the members belonging to the same base name will be replaced.
Example
When the source list contains:
_list{0}.foo = '0'
_list{1}.foo = '1'
_list{2}.foo = '2'
_list{3}.foo = '3'
_list{4}.foo = '4'
_list{0}.bar = 'A'
_list{1}.bar = 'B'
_list{2}.bar = 'C'
_list{3}.bar = 'D'
_list{4}.bar = 'E'
After slicing with Starting Element Index = 1 and Number of Elements to Slice = 3, the list will be replaced with:
_list{0}.foo = '1'
_list{1}.foo = '2'
_list{2}.foo = '3'
_list{0}.bar = 'B'
_list{1}.bar = 'C'
_list{2}.bar = 'D'
Note: This transformer contains a Python script which was tested with both Python 2.7 interpreter and Python 3.6 interpreter.
Parameters
    Source List Attribute:
Select a source list attribute to be sliced.
    Starting Element Index:
Specify index of the element to start slicing. The index is always 0-based.
If specified index is less than 0, this transformer considers the starting index as 0.
    Number of Elements to Slice:
Specify the number of elements to be sliced.
If specified number is equal to 0, this transformer removes every element from the source list (i.e. removes the source list).
If specified number is less than 0, this transformer considers the number as 0.
    Null Elements Treatment:
Select how treat <null> elements in the slicing range.
"Replace with Empty String" - Every <null> element will be replaced with an empty string.
"Replace with New Value" - Every <null> element will be replaced with a value specified as New Value for Null parameter.
"Replace with Missing" - Every <null> element will be removed. The element will be missing in the resultant list.
"Leave Null" - Every <null> element will be left in the resultant list as <null>.
    New Value for Null:
Specify a value to be used for replacing <null> elements.
This parameter is used only if you selected "Replace with New Value" to Null Elements Treatment. Otherwise, it'll be just ignored.
    Missing Elements Treatment:
Select how treat <missing> elements in the slicing range.
"Replace with Empty String" - Every <missing> element will be replaced with an empty string.
"Replace with New Value" - Every <missing> element will be replaced with a value specified as New Value for Missing parameter.
"Replace with Null" - Every <missing> element will be replaced with <null>.
"Leave Missing" - Every <missing> element will be still missing in the resultant list.
    New Value for Missing:
Specify a value to be used for replacing <missing> elements.
This parameter is used only if you selected "Replace with New Value" to Missing Elements Treatment. Otherwise, it'll be just ignored.

Parameters:
- SRC_LIST =   # " " Source List Attribute
- START_INDEX = 0   # Starting Element Index
- NUM_ELEMENTS =   # Number of Elements to Slice
- NULL_TREATMENT = empty
- NEWVALUE_FOR_NULL =   # New Value for Null
- MISSING_TREATMENT = empty
- NEWVALUE_FOR_MISSING =   # New Value for Missing

Input (input)
    -> ParameterFetcher
ParameterFetcher
    ATTR_LIST = __listslicer.src_list {$(SRC_LIST)} __listslicer.start_index {$(START_INDEX)} __listslicer.num_elements {$(NUM_ELEMENTS)} __listslicer.null_treat {$(NULL_TREATMENT)} __listslicer.newvalue_for_null {$(NEWVALUE_FOR_NULL)} __listslicer.missing_treat {$(MISSING_TREATMENT)} __listslicer.newvalue_for_missing {$(NEWVALUE_FOR_MISSING)}
    -> PythonCaller
PythonCaller
    HIDE_ATTRIBUTES = __listslicer.src_list __listslicer.start_index __listslicer.num_elements __listslicer.null_treat __listslicer.newvalue_for_null __listslicer.missing_treat __listslicer.newvalue_for_missing
    PYTHONSOURCE:
      # 2014-07-27, Takashi Iijima, Original Implementation
      # 2014-08-02, Takashi Iijima, Resolved encoding issue on list name
      # 2018-06-14, Takashi Iijima, Updated to support both Python 2.7 and Python 3.x
      # 2020-04-30, Takashi Iijima, Changed default Python interpreter version to 3.x, saved with FME 2017.1.2.1

      import fmeobjects, re

      class ListSlicer(object):
          def __init__(self):
              import platform
              if platform.python_version_tuple()[0] == '2':
                  import locale
                  loc = locale.getdefaultlocale()
                  enc = loc[1] if loc else 'utf_8'
                  self.toStr = lambda s: s.encode(enc) if isinstance(s, unicode) else s
              else:
                  self.toStr = lambda s: s

          def input(self, feature):
              listName = self.toStr(feature.getAttribute('__listslicer.src_list'))
              prefix = listName[:-2]
              regexListElement = re.compile(r'^%s\{(\d+)\}(.*)$' % prefix)

              # Find maximum element index and collect suffixes of target list members.
              maxIndex = -1
              suffixes = set([])
              for name in [self.toStr(s) for s in feature.getAllAttributeNames()]:
                  m = regexListElement.match(name)
                  if m:
                      if maxIndex < int(m.group(1)):
                          maxIndex = int(m.group(1))
                      suffixes.add(self.toStr(m.group(2)))

              startIndex = int(feature.getAttribute('__listslicer.start_index'))
              if startIndex < 0:
                  startIndex = 0
              numElements = int(feature.getAttribute('__listslicer.num_elements'))
              if numElements < 0:
                  numElements = 0

              nullTreat = feature.getAttribute('__listslicer.null_treat')
              newValueToNull = feature.getAttribute('__listslicer.newvalue_for_null')

              missingTreat = feature.getAttribute('__listslicer.missing_treat')
              newValueToMissing = feature.getAttribute('__listslicer.newvalue_for_missing')

              for suffix in suffixes:
                  # Move elements from slicing range to head of the list.
                  for i in range(numElements):
                      srcName = '%s{%d}%s' % (prefix, startIndex + i, suffix)
                      destName = '%s{%d}%s' % (prefix, i, suffix)

                      isNull, isMissing, type = feature.getAttributeNullMissingAndType(srcName)
                      if isNull:
                          if nullTreat == 'empty':
                              feature.setAttribute(destName, '')
                          elif nullTreat == 'newvalue':
                              feature.setAttribute(destName, newValueToNull)
                          elif nullTreat == 'missing':
                              feature.removeAttribute(destName)
                          elif nullTreat == 'as_is':
                              feature.setAttributeNullWithType(destName, type)
                          else:
                              raise fmeobjects.FMEException('Debug error: Null Treatment')

                      elif isMissing:
                          if missingTreat == 'empty':
                              feature.setAttribute(destName, '')
                          elif missingTreat == 'newvalue':
                              feature.setAttribute(destName, newValueToMissing)
                          elif missingTreat == 'null':
                              feature.setAttributeNullWithType(destName, type)
                          elif missingTreat == 'as_is':
                              feature.removeAttribute(destName)
                          else:
                              raise fmeobjects.FMEException('Debug error: Missing Treatment')

                      else:
                          feature.setAttribute(destName, feature.getAttribute(srcName))

                  # Remove excess elements.
                  for i in range(numElements, maxIndex + 1):
                      feature.removeAttribute('%s{%d}%s' % (prefix, i, suffix))

              feature.removeAttrsWithPrefix('__listslicer.')
              self.pyoutput(feature)

          def close(self):
              pass
    PYTHONSYMBOL = ListSlicer
    -> Output (output)
Output (output)

FME custom transformer CreatingHashKeyFromAttributes_2
Description 
This custom transformer is using a hashing function in order to create a unique identifier (value) for a metadata records.  Strategic fields (attributes) from the metadata records are used in the hashing function in order to create a very representative unique value for each metadata records.
Input Ports 
Input: The input metadata records to process.
Output Ports 
OUTPUT: The output metdata records with an attribute representing a unique hash value for the metadata record (_global_hashkey)
Parameters 
ID_ATT: Name of the attribute containing the identification of the metadata record
DATESTAMP_ATT: Name of the attribute containing the date stamp of the metadata record 
RES_URL_ATT: Name of the attribute containing the resource URL of the metadata record
RES_NAME_ATT: Name of the attribute containing the resource name of the metadata record
TITLE_ATT: Name of the attribute containing the title of the metadata record
ABSTRACT_ATT: Name of the attribute containing the description of the abstract of the metadata record
RES_FORMAT_ATT: Name of the attribute containing the format of the resource of the metadatarecord

Parameters:
- ID_ATT =
- DateStamp_ATT =
- Resources_URL_ATT =
- Resources_Name_ATT =
- Title_ATT =
- Abstract_ATT =
- Resources_Format_ATT =

Cloner_Input (input)
    -> AttributeCreator_4
AttributeKeeper_Output (output)

Bookmark: Creating hasing key to evaluate value
AttributeCreator_4
    ATTR_TABLE:
      SET_TO ID_ATT = $(ID_ATT)
      SET_TO TITLE_ATT = $(Title_ATT)
      SET_TO ABSTRACT_ATT = $(Abstract_ATT)
      SET_TO DATESTAMP_ATT = $(DateStamp_ATT)
      SET_TO RESOURCES_NAME_ATT = $(Resources_Name_ATT)
      SET_TO RESOURCES_URL_ATT = $(Resources_URL_ATT)
      SET_TO RESOURCES_FORMAT_ATT = $(Resources_Format_ATT)
    -> PythonCaller_2
Note: Creating hash key
PythonCaller_2
    PYTHONSOURCE:
      import fme
      import fmeobjects
      import hashlib
      # Template Function interface:
      # When using this function, make sure its name is set as the value of
      # the 'Class or Function to Process Features' transformer parameter

      class FeatureProcessor(object):
          def __init__(self):
              pass
          def input(self,feature):
              # Create the hash value for the ID
              id=feature.getAttribute(feature.getAttribute('ID_ATT')).replace('\t',' ').lstrip(' ').rstrip(' ')
              id_haskey=hashlib.sha256(id.encode('utf-8')).hexdigest()
      #        feature.setAttribute('_hash_id',id_haskey)

              # Create the hash value for the Date stamp
              datestamp=feature.getAttribute(feature.getAttribute('DATESTAMP_ATT')).replace('\t',' ').lstrip(' ').rstrip(' ')
              datestamp_haskey=hashlib.sha256(datestamp.encode('utf-8')).hexdigest()
      #        feature.setAttribute('_hash_datestamp',datestamp_haskey)

              # Create the hash value for the Abstract
              abstract=feature.getAttribute(feature.getAttribute('ABSTRACT_ATT')).replace('\n', ' ').replace('\r', '').replace('\t',' ').lstrip(' ').rstrip(' ')
              abstract_haskey=hashlib.sha256(abstract.encode('utf-8')).hexdigest()
      #        feature.setAttribute('_hash_abstract',abstract_haskey)

              # Create the hash value for the Title
              title=feature.getAttribute(feature.getAttribute('TITLE_ATT')).replace('\n', ' ').replace('\r', '').replace('\t',' ').lstrip(' ').rstrip(' ')
              title_haskey=hashlib.sha256(title.encode('utf-8')).hexdigest()
      #        feature.setAttribute('_hash_title',title_haskey)

              ## Create the hash value for the esources URL
              res_url=feature.getAttribute(feature.getAttribute('RESOURCES_URL_ATT'))
              url_hash=[]
              if res_url:
                  # Loop over each resources URL if it is a list
                  for url in res_url:
                      url_hash.append(hashlib.sha256(url.lstrip(' ').rstrip(' ').encode('utf-8')).hexdigest())

                  if len(url_hash)>1:
                      url_hash.sort()
                      url_hash=hashlib.sha256(''.join(url_hash).encode('utf-8')).hexdigest()
                  else:
                      url_hash=''.join(url_hash)
              else:
                  # It's not a list
                  res_url=feature.getAttribute(feature.getAttribute('RESOURCES_URL_ATT').replace('{}',''))
                  url_hash=hashlib.sha256(res_url.encode('utf-8')).hexdigest()
      #        feature.setAttribute('_hash_url',url_hash)

              # Create the hash value for the Resource_name
              res_name=feature.getAttribute(feature.getAttribute('RESOURCES_NAME_ATT'))
              name_hash=[]
              if res_name:
                  # Loop over each resources name if it is a list
                  for name in res_name:
                      name_hash.append(hashlib.sha256(name.replace('\t',' ').lstrip(' ').rstrip(' ').encode('utf-8')).hexdigest())

                  if len(name_hash)>1:
                      name_hash.sort()
                      name_hash=hashlib.sha256(''.join(name_hash).encode('utf-8')).hexdigest()
                  else:
                      name_hash=''.join(name_hash)
              else:
                  # It is not a list
                  res_name=feature.getAttribute(feature.getAttribute('RESOURCES_NAME_ATT').replace('{}',''))
                  name_hash=hashlib.sha256(res_name.encode('utf-8')).hexdigest()
      #        feature.setAttribute('_hash_name',name_hash)

              # Create the hash value for the Resource_format
              if feature.getAttribute('RESOURCES_FORMAT_ATT'):
                  res_format=feature.getAttribute(feature.getAttribute('RESOURCES_FORMAT_ATT'))
                  format_hash=[]
                  if res_format:
                      for format in res_format:
                          format_hash.append(hashlib.sha256(format.replace('\t',' ').lstrip(' ').rstrip(' ').encode('utf-8')).hexdigest())

                      if len(format_hash)>1:
                          format_hash.sort()
                          format_hash=hashlib.sha256(''.join(format_hash).encode('utf-8')).hexdigest()
                      else:
                          format_hash=''.join(format_hash)

                  else:
                      res_format=feature.getAttribute(feature.getAttribute('RESOURCES_FORMAT_ATT').replace('{}',''))
                      format_hash=hashlib.sha256(res_format.encode('utf-8')).hexdigest()

      #            feature.setAttribute('_hash_format',format_hash)
              else:
                  format_hash='not_validated'
      #            feature.setAttribute('_hash_format',format_hash)

              # Create the glabal hash value by using all the intermediate hash values
              global_string='%s%s%s%s%s%s%s'%(id_haskey,datestamp_haskey,abstract_haskey,title_haskey,url_hash,name_hash,format_hash)
              hashkey=hashlib.sha256(global_string.encode('utf-8'))
              feature.setAttribute('_global_hashkey',hashkey.hexdigest())

              self.pyoutput(feature)
          def close(self):
              pass
    PYTHONSYMBOL = FeatureProcessor
    -> AttributeRemover
AttributeRemover
    REMOVE_ATTRS = RESOURCES_NAME_ATT,RESOURCES_URL_ATT,ID_ATT,DATESTAMP_ATT,ABSTRACT_ATT,TITLE_ATT
    -> AttributeKeeper_Output (output)
