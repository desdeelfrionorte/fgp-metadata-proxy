FME workspace MB_SK_DEV.fmw
Title: MB_SK_DEV
Description: Description 
This workbench read and trasform all the metadata for the provinces of Manitoba (MB) and Saskatchewan (SK).
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
DCAT_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the DCAT_READER. This file is used when the parameter: DCAT_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P-T_ABBR: Two or three letter abbreviation code of the province or terrirtory (ex.: ON, QC, PEI, ...).
METADATA_OVERWRITE: Enable the overwite of the PyCSW.  Can take two values: Yes: Overwrite the contentof the PyCSW; No: Do no overwrite the content of the PyCSW.
IN_OUT_WORKING_DIR: Root working directory defined by default as: (FME_SHAREDRESOURCE_DATA)\ PT_Harvester.  Used to define the following private parameters:
IN_CSV_LOOKUP_TABLES_DIR: Source directory of the root of the lookup table files. Defined as: (IN_OUT_WORKING_DIR)\ LOOKUP_TABLES
IN_GMD_XML_TEMPLATE_DIR: Source directory of the root XML templates. Defined as: (IN_OUT_WORKING_DIR)\ XML_TEMPLATES
IN_TBS_JSON_TEMPLATE_DIR: Source directory of the root JSON templates. Defined as: (IN_OUT_WORKING_DIR)\ JSON_TEMPLATES
LOG_FILE: Output log file. Defined as: (IN_OUT_WORKING_DIR)\ (P-T_ABBR)\ LOG\ (P-T_ABBR).log
OUT_JSON_LOCAL_DIR: Source directory to output JSON files. Defined as: (IN_OUT_WORKING_DIR)\ (P-T_ABBR)\ JSON_LOCAL
OUT_XLS_NOTIFICATION_DIR: Source directory to output excel files. Defined as: (IN_OUT_WORKING_DIR)\ (P-T_ABBR)\ XLS
OUT_XML_FAILED_DIR: Source directory to output failed XML files. Defined as: (IN_OUT_WORKING_DIR)\ (P-T_ABBR)\ XML_FAILED
OUT_XML_LOCAL_DIR: Source directory to output Local Source XML files. Defined as: (IN_OUT_WORKING_DIR)\ (P-T_ABBR)\ XML_LOCAL
OUT_XML_PASSED_DIR: Source directory to output passedXML files. Defined as: (IN_OUT_WORKING_DIR)\ (P-T_ABBR)\ XML_PASSED
URL_VALIDATION : Indicates to validate or not created URL. (Should be Yes for prod)

Parameters:
- ACTIVATE_GEO = Yes
- ACTIVATE_NON_GEO = No
- ACTIVATE_TRANSLATION = Yes
- DCAT_READER_SELECT = Yes
- FORCED_PYCSW_URL =
- IN_FFS_TESTING_FILE =
- LOCAL_SOURCE_METADATA_DELTA_FINDER = No
- LOCAL_WRITER = No
- P-T_ABBR = MB
- METADATA_OVERWRITE = NO   # METADATA OVERWRITE
- IN_OUT_WORKING_DIR = $(FME_SHAREDRESOURCE_DATA)\PT_Harvester
- SAMPLE_SIZE = 0
- URL_VALIDATION = Yes
- IN_CSV_LOOKUPTABLES_DIR = $(IN_OUT_WORKING_DIR)\LOOKUP_TABLES   # Lookup Tables Directory
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(IN_OUT_WORKING_DIR)

Note: Extracting 'identifier' from alternate strings to match the two sets of Dcat sources
Note: Ce bookmark n'est pas necesaire pour MB/SK
DCAT_Reader_2
    CUSTOM_PRIMARY = DCAT_P
    CUSTOM_SECONDARY = DCAT_S
    P-T = $(P-T_ABBR)
    -> DCAT_TO_CKAN_RENAMER
Note: extraction du système de référence spatiale basée sur l'URL et/ou format / L'url donne des fois un wkid et quand on a du kml/kmz c'est du 4326 ... Format natif de google earth
PythonCaller_2
    PYTHONSOURCE:
      import fme
      import fmeobjects
      from Python.FME_utils import FME_utils
      import urllib.parse


      # Template Function interface:
      # When using this function, make sure its name is set as the value of
      # the 'Class or Function to Process Features' transformer parameter
      def processFeature(feature):


          extracted_epsg=[]

          try:

              for i in range(FME_utils.max_index_attribute_list(feature,'resources{}')+1):
                  _url=urllib.parse.unquote(feature.getAttribute('resources{%i}.url'%(i))).lower()
                  _format=feature.getAttribute('resources{%i}.format'%(i)).lower()


                  if _url.find('latestwkid') !=-1:


                      epsg=int(_url.split('"latestwkid":')[1].split(',')[0])
                      extracted_epsg.append(epsg)


                  if _format=='kml' or _format=="kmz":
                      extracted_epsg.append(4326)

              j=0
              if extracted_epsg:
                  for elem in list(dict.fromkeys(extracted_epsg)):
                      feature.setAttribute('spatialref{%i}.projection'%(j),'EPSG: %i'%(elem))
                      feature.setAttribute('spatialref{%i}.projection_system'%(j),'EPSG')
                      feature.setAttribute('spatialref{%i}.projection_system_version'%(j),'unknown')
                      j+=1
              else:
                  feature.setAttribute('spatialref{0}.projection','unknown')
                  feature.setAttribute('spatialref{0}.projection_system','unknown')
                  feature.setAttribute('spatialref{0}.projection_system_version','unknown')

          except:

              feature.setAttribute('spatialref{0}.projection','unknown')
              feature.setAttribute('spatialref{0}.projection_system','unknown')
              feature.setAttribute('spatialref{0}.projection_system_version','unknown')
    PYTHONSYMBOL = processFeature
    -> RESOURCE_NAME_UNDERSCORE_REMOVER
Note: Writes XML to a local folder without publishing to PyCSW, and without the PyCSW transaction headers and footers
text_line (writer TEXTLINE_3)
    attributes: text_line_data buffer
text_line (writer TEXTLINE_1)
    attributes: text_line_data buffer
text_line (writer TEXTLINE_2)
    attributes: text_line_data buffer
invalid_metadata (writer XLSXW_1)
    attributes: id auto(20)

Bookmark: Lecture des données DCAT
Creator
    GEOMTYPE = Geometry Object
    NUM = 1
    CREATED -> Tester
Tester
    BOOL_OP = OR
    COMPOSITE_TEST = 1
    TEST_CLAUSE = TEST $(DCAT_READER_SELECT) = Yes
    TEST_MODE = TEST
    PASSED -> DCAT_Reader
    PASSED -> DCAT_Reader_2
    FAILED -> FeatureReader [INITIATOR]
Note: The GeoHub Service (in this version) is HARDCODED inside the Custom and depends on the P-T parameter
DCAT_Reader [off]
    CUSTOM_PRIMARY = DCAT_P
    CUSTOM_SECONDARY = DCAT_S
    P-T = $(P-T_ABBR)
    -> DCAT_TO_CKAN_RENAMER
Note: Reads pre-generated FFS file for testing as substitute for ARCGIS_HUB_READER
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> DCAT_TO_CKAN_RENAMER
DCAT_TO_CKAN_RENAMER
    IN_OUT_WORKING_DIR = $(FME_SHAREDRESOURCE_DATA)\PT_Harvester
    P-T_ABBR = $(P-T_ABBR)
    -> ATTRIBUTE_VALUE_TEXT_CLEANER
ATTRIBUTE_VALUE_TEXT_CLEANER
    -> TestFilter_3
AttributeExposer
    ATTR_LIST = license_info
    -> NullAttributeMapper
NullAttributeMapper
    ATTRCHOICE = Selected Attributes
    ATTRLIST = license_info
    NEW_VALUE = unknown
    NULL_TREATMENT = New Value
    SOURCE_ATTR_VAL = Null Empty "Missing (Selected Attributes Only)"
    -> LICENSE_FILTER_NG
LICENSE_FILTER_NG
    FEATURE_TYPE = License_$(P-T_ABBR)
    IN_CSV_LOOKUP_TABLES_DIR = $(IN_CSV_LOOKUPTABLES_DIR)
    LICENSE_ATT = @Value(license_info)
    P-T_ABBR = $(P-T_ABBR)
    LICENSE_FILTER_PASSED -> AttributeExposer_24
    UNKNOWN_LICENSE -> unknown_licence (writer XLSXW_1)
unknown_licence (writer XLSXW_1)
    attributes: license_id string(200), id string(200), title string(200)

Bookmark: Sampler
TestFilter_3
    DEFAULT_VALUE = SAMPLES FEATURES
    TEST_LIST = "BOOL_OP,OR,COMPOSITE_TEST,""""""1"""""",TEST_CLAUSE,TEST $(SAMPLE_SIZE) = 0",ALL FEATURES
    ALL FEATURES -> AttributeExposer
    SAMPLES FEATURES -> Sampler
Sampler
    RATE = $(SAMPLE_SIZE)
    SAMPLE_MODE = No
    SAMPLE_TYPE_LONG = First N Features
    SAMPLED -> AttributeExposer

Bookmark: Suppression des doublons
AttributeExposer_24
    ATTR_LIST = id
    -> DuplicateFilter
DuplicateFilter
    INPUT_ORDERED_CHOICE = No
    KEYATTR = id
    UNIQUE -> AttributeExposer_2

Bookmark: Renommer ArcGIS Hub Dataset par Original Metadata
AttributeExposer_2
    ATTR_LIST = resources{}.name
    -> ListSearcher
ListSearcher
    ATTR_VALUE = ArcGIS Hub Dataset
    INDEX_ATTR = _index_Landing_page
    LIST_ATTR = resources{}.name
    MATCHTYPE = FIRST_MATCHED_ENCODED
    FOUND -> AttributeCreator
    NOT_FOUND -> Junction_3
AttributeCreator
    ATTR_TABLE = SET_TO resources{@Value(_index_Landing_page)}.name = Original Metadata (https://geohub.saskatchewan.ca)
    -> Junction_3
Junction_3
    -> DEFAULT_ATTRIBUTE_MAPPER_NG

Bookmark: Filtering and converting to inhouse model.
Note: Creating default values for SK
DEFAULT_ATTRIBUTE_MAPPER_NG
    FEATURE_TYPE = Default_$(P-T_ABBR)
    IN_CSV_LOOKUP_TABLES_DIR = $(IN_CSV_LOOKUPTABLES_DIR)
    P-T_ABBR = $(P-T_ABBR)
    -> AttributeExposer_14

Bookmark: Date conversion
AttributeExposer_14
    ATTR_LIST = id,record_create_date,record_last_modified,record_publish_date
    -> DateTimeConverter
Note: Record created/modified/publish
DateTimeConverter
    DATETIME_ATTR = record_create_date record_last_modified record_publish_date
    OUT_FORMAT = %Y-%m-%d
    PASSTHROUGH = NO
    REPAIR_INPUT = YES
    -> Junction_2
    <REJECTED> -> AttributeRemover_2
AttributeRemover_2
    REMOVE_ATTRS = fme_rejection_code
    -> Junction_2
Junction_2
    -> AttributeExposer_15

Bookmark: Nettoyage des courriels
AttributeExposer_15
    ATTR_LIST = contact_email
    -> StringReplacer
StringReplacer
    CASE = NO
    FIND_TEXT = mailto:
    NO_MATCH = _FME_NO_OP_
    REGEXP = NO
    SRC_ATTRS = contact_email
    -> ATTRIBUTE_MANAGER_NG

Bookmark: Alternate Attribute manager
Note: Create Attributes
ATTRIBUTE_MANAGER_NG
    IN_YAML_TEXT:
      resource.id:
          action: attribute_overwrite
          attr2set: id

      update_frequency:
          action: text_not_null
          attr2set: Unknown

      record_publish_date:
          action: attribute_not_null
          attr2set: record_create_date

      online_resource_protocol:
          action: attribute_overwrite
          attr2set: resources{0}.type

      category:
          action: text_not_null
          attr2set: geoscientificInformation

      west_bound_longitude:
         action: attribute_not_null
         attr2set: default_west_bound_longitude

      east_bound_longitude:
         action: attribute_not_null
         attr2set: default_east_bound_longitude

      south_bound_latitude:
         action: attribute_not_null
         attr2set: default_south_bound_latitude

      north_bound_latitude:
         action: attribute_not_null
         attr2set: default_north_bound_latitude
    -> PythonCaller
Note: Si resources{}.name:Shapefile / alors, resources{}.format <- Shapefile
PythonCaller
    PYTHONSOURCE:
      import fme
      import fmeobjects
      # Template Function interface:
      # When using this function, make sure its name is set as the value of
      # the 'Class or Function to Process Features' transformer parameter
      def processFeature(feature):

          resources_name = feature.getAttribute('resources{}.name')

          #If no attribute then create empty attribute
          if not resources_name:
              pass
          else:
              for elem in range(len(resources_name)):
                  if resources_name[elem]=='Shapefile':
                      feature.setAttribute('resources{%i}.format'%(elem), 'Shapefile')
    PYTHONSYMBOL = processFeature
    -> AttributeExposer_4
AttributeExposer_4
    ATTR_LIST = resource.id
    -> UNIQUE_ID_CREATOR
UNIQUE_ID_CREATOR
    UNIQUE_ATT = @Value(resource.id)
    -> EMPTY_FORMAT_MAPPER_NG [DATA_INPUT]

Bookmark: Ajustement des formats et des ressources
EMPTY_FORMAT_MAPPER_NG
    CSV_FORMAT = Format
    CSV_MIME_TYPE = Mime_type
    IN_CSV_LOOKUP_TABLES_DIR = $(IN_CSV_LOOKUPTABLES_DIR)
    P-T_ABBR = $(P-T_ABBR)
    URL_VALIDATION = $(URL_VALIDATION)
    DATA_OUTPUT -> RESOURCES_VALIDATOR
    UNKNOWN_MIME_TYPE -> unknown_mine_type (writer XLSXW_1)
Note: Enlève les ressources sans url
RESOURCES_VALIDATOR
    -> GEO_NONE_GEO_SELECTOR
unknown_mine_type (writer XLSXW_1)
    attributes: id string(200), UNIQUE_ATT string(200), resource.id string(200), _unknown_mime_type string(200)

Bookmark: Filtrage geo / non-geo
GEO_NONE_GEO_SELECTOR
    CSV_FILE_NAME = GeoSpatialValidation
    CSV_PATH = $(IN_CSV_LOOKUPTABLES_DIR)
    CSV_PROVINCE = $(P-T_ABBR)
    YAML_DIRECTIVES:
      resources{}.format:
        domain: lookup_table_format
        spatial_type: overwrite
        not_found: log
        search_type: equals
    GEOSPATIAL -> SPATIAL_TYPE_MAPPER_NG [DATA_INPUT]
    NONE_GEOSPATIAL -> MANUAL_GEOSPATIAL_SETTER_NG [DATA_INPUT]
    LOG_ERROR -> unknown_format (writer XLSXW_1)
SPATIAL_TYPE_MAPPER_NG
    FEATURE_TYPE = SpatialType_$(P-T_ABBR)
    IN_CSV_LOOKUP_TABLES_DIR = $(IN_CSV_LOOKUPTABLES_DIR)
    P-T_ABBR = $(P-T_ABBR)
    DATA_OUTPUT_FAILED -> Spatial_Type_Mapper_Failed (writer XLSXW_1)
    DATA_OUTPUT_PASSED -> TestFilter
Spatial_Type_Mapper_Failed (writer XLSXW_1)
    attributes: id string(20), title string(80), url string(80)
unknown_format (writer XLSXW_1)
    attributes: format auto(20)
MANUAL_GEOSPATIAL_SETTER_NG
    FEATURE_TYPE = UnmappedGeoData_$(P-T_ABBR)
    IN_CSV_LOOKUP_TABLES_DIR = $(IN_CSV_LOOKUPTABLES_DIR)
    P-T_ABBR = $(P-T_ABBR)
    GEOSPATIAL -> TestFilter
    UNMAPPED_DATA -> unmapped_data (writer XLSXW_1)
TestFilter
    DEFAULT_VALUE = <UNFILTERED>
    TEST_LIST = "BOOL_OP,OR,COMPOSITE_TEST,""""""1"""""",TEST_CLAUSE,CASE_INSENSITIVE_TEST @LowerCase($(ACTIVATE_GEO)) = yes",GEO_ACTIVATE
    GEO_ACTIVATE -> METADATA_VALUE_MAPPER_NG_2 [DATA_INPUT]
unmapped_data (writer XLSXW_1)
    attributes: id string(200), notes string(200), title string(200), url string(200)

Bookmark: Metadata Value Mapping - GEO
Note: Topic (categfory)
METADATA_VALUE_MAPPER_NG_2
    ATT_TO_MAP = category
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_3 [DATA_INPUT]
Note: Role
METADATA_VALUE_MAPPER_NG_3
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: Update
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: Progress
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_7 [DATA_INPUT]
Note: SpatialRepresentation
METADATA_VALUE_MAPPER_NG_7
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> GEO_ATTRIBUTE_MAPPING_ERRORS (writer XLSXW_1)
    DATA_OUTPUT -> PythonCaller_2
GEO_ATTRIBUTE_MAPPING_ERRORS (writer XLSXW_1)
    attributes: error string(200), id string(200), _element_index string(200)

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    URL_VALIDATION = Yes
    -> WMS_REST_LANGUAGE_FORMATTER
    FAULTY_URL_OUTPUT -> MAP_SERVICE_URL_ERRORMAP (writer XLSXW_1)
MAP_SERVICE_URL_ERRORMAP (writer XLSXW_1)
    attributes: id string(200), url string(200), format string(200), _url_failure_message string(200)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> AttributeCreator_3

Bookmark: New Bookmark
AttributeCreator_3
    ATTR_TABLE = SET_TO csw_url = $(FORCED_PYCSW_URL)
    -> AttributeExposer_13
AttributeExposer_13
    ATTR_LIST = search_criteria_pycsw
    -> METADATA_DELTA_FINDER_NG
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> StatisticsCalculator_Summary_2
    Update -> Junction
    Insert -> Junction
    Delete -> DELETEDRECORDS (writer XLSXW_1)
StatisticsCalculator_Summary_2: Logger
    LOG_FEATURE = NONE
    MAXFEATS = 20
    MESSAGE:
      ************************
      **** Unchanged Report ****
      ************************

      @Value(_real_count) features were unchanged

      ************************
      ************************
      ************************
    SEVERITY = INFO
Junction
    -> AWS_TRANSLATE_2
DELETEDRECORDS (writer XLSXW_1)
    attributes: _timestamp string(200), id string(200)

Bookmark: AWS Translation
AWS_TRANSLATE_2
    ACTIVATE_TRANSLATION = $(ACTIVATE_TRANSLATION)
    ATTR_2_TRANSLATE = notes,title
    ATTR_LIST_2_TRANSLATE = tags{}.value,resources{}.name
    MODE = English-->French
    -> XML_PUBLISHER_NG
    TRANSLATION_PROBLEM -> Translation_errors (writer XLSXW_1)
Translation_errors (writer XLSXW_1)
    attributes: id string(20), _timestamp string(20)

Bookmark: XML CREATION AND WRITING
XML_PUBLISHER_NG
    FEATURE_TYPE = Config_$(P-T_ABBR)
    IN_CSV_LOOKUP_TABLES_DIR = $(IN_CSV_LOOKUPTABLES_DIR)
    LOCAL_WRITER = $(LOCAL_WRITER)
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> invalid_metadata (writer XLSXW_1)
    UPDATE_FAILED -> text_line (writer TEXTLINE_2)

FME custom transformer DCAT_Reader
Description
This Custom Transformer is used to read ESRI GeoHub DCAT server.  GeoHub DCAT reader is using two server extractions (a primary and a secondary) to extract a complete set of DCAT metadata for each record.  Metadata extracted from the primary server extracttion are prefixed wirh DCAT_P whereas the the metadata extracted from the secondary server extraction are prefixed with DCAT_S.  In order to join the metadata from the primary and the secondary extraction both extraction must share a common identifier when no common identifier are found the is no secondary metadata with the prfix DCAT_S.
Note: There is no option to read only one record with a specific identifier.
Input Ports
Input: One feature to start the extraction of all the records from the GeoHub DCAT server.
Output Ports
Résultats: All the records read from the GeoHub DCAT server.
Parameters
GEO_HUB_SERVICE: Name of the DCAT servers to use. Choices are:
Manitoba GeoHub: To read Manitoba GeoHub;
Saskatchewan GeoHub: To read Sakatchewan GeoHub;
Custom GeoHub: To enter specific values of primary and secondary url;
CUSTOM_PRIMARY: Definition of the primary Geo Hub service. Used when the option Custom GeoHub is selected;
CUSTOM_SECONDARY: Definition of the seconary Geo Hub service. Used when the option Custom GeoHub is selected.  It is possible to leave this field empty, in that case no secondary service will be read and less metadata will be extracted.

Parameters:
- CUSTOM_PRIMARY =
- TEXT =   # CUSTOM_SECONDARY CUSTOM_SECONDARY
- P-T = SK

Input (input)
    -> TestFilter
AttributeExposer
    ATTR_LIST = DCAT_P_identifier
    -> AttributeSplitter
AttributeSplitter
    ATTR_NAME = DCAT_P_identifier
    DELIMITER = =
    DROP_EMPTY_PARTS = No
    LIST_NAME = _iden
    TRIM_OPTION = Both
    -> AttributeSplitter_2
AttributeSplitter_2
    ATTR_NAME = _iden{1}
    DELIMITER = &
    DROP_EMPTY_PARTS = No
    LIST_NAME = _identifier
    TRIM_OPTION = Both
    -> AttributeCopier
AttributeCopier
    ATTR_TABLE = COPY _identifier{0} > identifier
    -> AttributeRemover_2
AttributeRemover_2
    LIST_ATTRS = _iden{} _identifier{}
    -> FeatureMerger [REQUESTOR]
AttributeExposer_2
    ATTR_LIST = _response_body_S
    -> AttributeSplitter_3
AttributeSplitter_3
    ATTR_NAME = _response_body_S
    DELIMITER = "id": "
    DROP_EMPTY_PARTS = No
    LIST_NAME = _respon
    TRIM_OPTION = Both
    -> AttributeSplitter_4
AttributeSplitter_4
    ATTR_NAME = _respon{1}
    DELIMITER = "
    DROP_EMPTY_PARTS = No
    LIST_NAME = _response
    TRIM_OPTION = Both
    -> AttributeCopier_2
AttributeCopier_2
    ATTR_TABLE = COPY _response{0} > identifier
    -> AttributeRemover_3
AttributeRemover_3
    LIST_ATTRS = _respon{} _response{}
    -> FeatureMerger [SUPPLIER]
Output (output)

Bookmark: DCAT_Reader
TestFilter
    DEFAULT_VALUE = Custom GeoHub
    TEST_LIST = "BOOL_OP,OR,COMPOSITE_TEST,""""""1"""""",TEST_CLAUSE,TEST $(P-T) = MB",Manitoba GeoHub,"BOOL_OP,OR,COMPOSITE_TEST,""""""1"""""",TEST_CLAUSE,TEST $(P-T) = SK",Saskatchewan GeoHub
    Manitoba GeoHub -> AttributeCreator_5
    Saskatchewan GeoHub -> AttributeCreator_6
    Custom GeoHub -> AttributeCreator_7
Junction_2
    -> AttributeCreator_2
    -> Tester_2
Note: Validate that a secondary URL is present
Tester_2
    BOOL_OP = OR
    COMPOSITE_TEST = 1
    TEST_CLAUSE = TEST @Value(_url_dcat_secondary) != ""
    TEST_MODE = TEST
    PASSED -> AttributeCreator
Note: Merge primary and secondary extraction
FeatureMerger
    ATTR_ACCUM_MODE = Merge Supplier
    ATTR_CONFLICT_RES = Use Requestor
    IGNORE_NULLS = No
    JOIN_KEYS = identifier identifier AUTO
    MERGE_TYPE = Attributes Only
    PROCESS_DUPS = NO
    REJECT_NULL_MISSING_KEYS = No
    SUPPLIERS_FIRST = No
    MERGED -> JSONFlattener
    UNMERGED_REQUESTOR -> JSONFlattener_3
    <REJECTED> -> Cloner
Note: Flatten the JSON from the Primary extraction
JSONFlattener
    ERROR_LIST_ATTR = _json_error
    JSON_DOCUMENT = @Value(_response_body_P)
    PREFIX_STRING = DCAT_P_
    READ_FROM_FILE = NO
    RECURSIVE = Yes
    -> JSONFlattener_2
    <REJECTED> -> Terminator
Note: Flattend the JSON from the Secondary extraction
JSONFlattener_2
    ERROR_LIST_ATTR = _json_error
    JSON_DOCUMENT = @Value(_response_body_S)
    PREFIX_STRING = DCAT_S_
    READ_FROM_FILE = NO
    RECURSIVE = Yes
    -> AttributeRemover
    <REJECTED> -> Terminator_2
Terminator_2
    MESSAGE = Unable to flatten secondary JSON extraction.  Translation Terminated
Terminator
    MESSAGE = Unable to flatten primary JSON extraction.  Translation Terminated
Note: Flatten the JSON from the Primary extraction
JSONFlattener_3
    ERROR_LIST_ATTR = _json_error
    JSON_DOCUMENT = @Value(_response_body_P)
    PREFIX_STRING = DCAT_S_
    READ_FROM_FILE = NO
    RECURSIVE = Yes
    -> AttributeRemover
    <REJECTED> -> Terminator_3
AttributeRemover
    REMOVE_ATTRS = _status_code,_status_code_description,_type_requete,_response_body_P,_response_body_S,DCAT_P_identifier,DCAT_S_slug_id_,_url_dcat_primary,_url_dcat_secondary
    -> Output (output)
Terminator_3
    MESSAGE = Unable to flatten primary JSON extraction.  Translation Terminated
Note: To disable Termination
Cloner
    COPIES = 1
    COPYATT = _copynum

Bookmark: Assign primary and secondary server URL
Note: Former url for primary metadata
AttributeCreator_5
    ATTR_TABLE:
      SET_TO _url_dcat_primary = https://geoportal.gov.mb.ca/data.json
      SET_TO _url_dcat_secondary = https://geoportal.gov.mb.ca/api/v3/datasets?filter[owner]=Manitoba_Government&page[number]=1&page[size]=25
    -> Junction_2
AttributeCreator_6
    ATTR_TABLE:
      SET_TO _url_dcat_primary = https://geohub.saskatchewan.ca/data.json
      SET_TO _url_dcat_secondary = https://geohub.saskatchewan.ca/api/v3/datasets?filter[owner]=Saskatchewan.Government&page[number]=1&page[size]=25
    -> Junction_2
AttributeCreator_7
    ATTR_TABLE:
      SET_TO _url_dcat_primary = $(CUSTOM_PRIMARY)
      SET_TO _url_dcat_secondary = $(CUSTOM_SECONDARY)
    -> Junction_2

Bookmark: DCAT primary extraction
AttributeCreator_2
    ATTR_TABLE = SET_TO _type_requete = DCAT-PRIMARY
    -> PythonCaller_1
Note: HTTP call for reading the Primary DCAT server
PythonCaller_1
    NEW_ATTRIBUTES = _response_body_P _status_code _status_code_description DCAT_P_identifier
    PYTHONSOURCE = from Python.DCAT_Reader import ManageHttpCall
    PYTHONSYMBOL = ManageHttpCall
    -> TestFilter_3
Note: Test if error duing the DCAT server extraction
TestFilter_3
    DEFAULT_VALUE = Other Error
    TEST_LIST = "BOOL_OP,OR,COMPOSITE_TEST,""""""1"""""",TEST_CLAUSE,TEST @Value(_status_code) = 200",200 OK
    200 OK -> FeatureMerger [REQUESTOR] [off]
    200 OK -> AttributeExposer
    Other Error -> Terminator_4
Terminator_4
    MESSAGE = Translation Terminated

Bookmark: DCAT secondary extraction
AttributeCreator
    ATTR_TABLE = SET_TO _type_requete = DCAT-SECONDARY
    -> PythonCaller_2
Note: HTTP call for reading the Secondary DCAT server
PythonCaller_2
    NEW_ATTRIBUTES = _response_body_S _status_code _status_code_description DCAT_S_slug_id_
    PYTHONSOURCE = from Python.DCAT_Reader import ManageHttpCall
    PYTHONSYMBOL = ManageHttpCall
    -> TestFilter_2
Note: Test if error duing the DCAT server extraction
TestFilter_2
    DEFAULT_VALUE = Other Error
    TEST_LIST = "BOOL_OP,OR,COMPOSITE_TEST,""""""1"""""",TEST_CLAUSE,TEST @Value(_status_code) = 200",200 OK
    200 OK -> FeatureMerger [SUPPLIER] [off]
    200 OK -> AttributeExposer_2
    Other Error -> Terminator_5
Terminator_5
    MESSAGE = Translation Terminated
