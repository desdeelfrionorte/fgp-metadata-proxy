FME workspace NB_PROD.fmw
Title: NB_BUILDER
Description: Description 
This workbench read and trasform all the metadata for the province of New Brunswick (NB)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...). Extracted automatically using a Python script from the name of the FME Workspace (ex.: NB_PROD.fmw)
METADATA_OVERWRITE: Enable the overwite of the PyCSW.  Can take two values: Yes: Overwrite the content of the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: .\NB\LOG\NB.log
OUT_JSON_LOCAL_DIR: Source directory to output JSON files. Defined as: \NB\JSON_LOCAL
OUT_XLS_NOTIFICATION: Source directory to output excel files. Defined as: \NB\XLS
OUT_XML_FAILED_DIR: Source directory to output failed XML files. Defined as: \NB\XML_FAILED
OUT_XML_LOCAL_DIR: Source directory to output Local Source XML files. Defined as: \NB\XML_LOCAL
OUT_XML_PASSED_DIR: Source directory to output passedXML files. Defined as: \NB\XML_PASSED
SAMPLE_SIZE: Number of features to process. Zero (0) means process all the features. A number n greater than 0 means sample or process only the first n features.
URL_VALIDATION : Indicates to validate or not created URL. (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = YES
- IN_OUT_WORKING_DIR = $(FME_SHAREDRESOURCE_DATA)\PT_Harvester
- SAMPLE_SIZE = 0
- URL_VALIDATION = Yes
- IN_CSV_LOOKUPTABLES_DIR = $(IN_OUT_WORKING_DIR)\LOOKUP_TABLES   # Lookup Tables Directory
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\NB.log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_LOCAL_DIR = $(IN_OUT_WORKING_DIR)\$(P-T_ABBR)\XML_LOCAL
- OUT_XML_FAILED_DIR = $(IN_OUT_WORKING_DIR)\$(P-T_ABBR)\XML_FAILED
- OUT_XML_PASSED_DIR = $(IN_OUT_WORKING_DIR)\$(P-T_ABBR)\XML_PASSED
- FME_SHAREDRESOURCE_DATA = C:\Data   # FME Server Resource Data

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

TestFilter
    DEFAULT_VALUE = <UNFILTERED>
    TEST_LIST = "BOOL_OP,OR,COMPOSITE_TEST,""""""1"""""",TEST_CLAUSE,TEST @LowerCase($(ACTIVATE_GEO)) = yes",GEO_ACTIVATE
    GEO_ACTIVATE -> TestFilter_3
Junction
    -> Socrata_BoundingBoxExtractor [feature_input]
Note: Extraction des coordonnées du BBOX
Socrata_BoundingBoxExtractor: SOCRATA_BOUNDING_BOX_EXTRACTOR
    DOMAIN = https://gnb.socrata.com
    SocrataAppToken = FL3Cxsebg0Vf6JQ0CnbMujHkQ
    URL_VALIDATION = Yes
    feature_output -> METADATA_VALUE_MAPPER_NG [DATA_INPUT]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
invalid_metadata (writer XLSXW_1)
    attributes: id auto(20)
TestFilter_2
    DEFAULT_VALUE = <UNFILTERED>
    TEST_LIST = "BOOL_OP,OR,COMPOSITE_TEST,""""""1"""""",TEST_CLAUSE,TEST @LowerCase($(ACTIVATE_NON_GEO)) = yes",NON-GEO_ACTIVATE
    NON-GEO_ACTIVATE -> TestFilter_4
Junction_2
    -> ATTRIBUTE_MANAGER_NG_6

Bookmark: lecture des données du portail socrata, filtrage de licence et fusion des métadonnées de vue externe
Creator_3
    GEOMTYPE = Geometry Object
    NUM = 1
    CREATED -> Tester_6
Tester_6
    BOOL_OP = OR
    COMPOSITE_TEST = 1
    TEST_CLAUSE = TEST $(CATALOGUE_READER_SELECT) = Yes
    TEST_MODE = TEST
    PASSED -> SOCRATA_READER_NG
    FAILED -> FeatureReader_2 [INITIATOR]
SOCRATA_READER_NG
    DOMAIN = "https://gnb.socrata.com "
    -> AttributeExposer_3
FeatureReader_2
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> AttributeExposer_3
AttributeExposer_3
    ATTR_LIST = licenseId,id,title
    -> NullAttributeMapper
Note: If there is no license: modify value to unknown (fgp_publish=non)
NullAttributeMapper
    ATTRCHOICE = Selected Attributes
    ATTRLIST = licenseId
    NEW_VALUE = unknown
    NULL_TREATMENT = New Value
    SOURCE_ATTR_VAL = "Missing (Selected Attributes Only)"
    -> LICENSE_FILTER_NG
LICENSE_FILTER_NG
    FEATURE_TYPE = License_NB
    IN_CSV_LOOKUP_TABLES_DIR = $(IN_CSV_LOOKUPTABLES_DIR)
    LICENSE_ATT = @Value(licenseId)
    P-T_ABBR = $(P-T_ABBR)
    LICENSE_FILTER_PASSED -> SOCRATA_METADATA_MERGER
    UNKNOWN_LICENSE -> unknown_licence (writer XLSXW_1)
SOCRATA_METADATA_MERGER
    DOMAIN = https://gnb.socrata.com
    -> DEFAULT_ATTRIBUTE_MAPPER_NG
    UnmergedAdvancedView -> unmergedAdvancedView (writer XLSXW_1)
unmergedAdvancedView (writer XLSXW_1)
    attributes: url string(200), format string(200), _seriesID string(200)
unknown_licence (writer XLSXW_1)
    attributes: license_id string(200), id string(200), title string(200)

Bookmark: Transformation vers modèle de travail et ajout des valeurs par défeauts
Note: Set default attribute values
DEFAULT_ATTRIBUTE_MAPPER_NG
    FEATURE_TYPE = Default_NB
    IN_CSV_LOOKUP_TABLES_DIR = $(IN_CSV_LOOKUPTABLES_DIR)
    P-T_ABBR = $(P-T_ABBR)
    -> AttributeExposer_13
Note: Gestion des attributs
ATTRIBUTE_MANAGER_NG
    IN_YAML_TEXT:
      # Create a new resource.id attribute
      resource.id:
          action: attribute_overwrite
          attr2set: id
      #
      # Create a new resource.type attribute
      resource.type:
          action: attribute_overwrite
          attr2set: assetType
      #
      # Default value for tags{} if null
      tags{0}:
          action: attribute_not_null
          attr2set: default_domain_tag
      #
      # Default value for category if null
      category:
          action: attribute_not_null
          attr2set: default_category
      #
      # Create a new sector attribute
      sector:
          action: attribute_overwrite
          attr2set: metadata.custom_fields.Department / Ministère.Department / Ministère
      #
      # Création de l'attribut pour record_last_modified
      record_last_modified:
          action: attribute_overwrite
          attr2set: viewLastModified
      #
      # Création de l'attribut pour record_publish_date
      record_publish_date:
          action: attribute_overwrite
          attr2set: publicationDate
      #
      # Création de l'attribut pour record_create_date
      record_create_date:
          action: attribute_overwrite
          attr2set: createdAt
    -> ATTRIBUTE_MANAGER_NG_2
Note: Utiliser l'attribut attribution s'il n'y pas sector défini
ATTRIBUTE_MANAGER_NG_2
    IN_YAML_TEXT:
      # Set attribution if sector_temps is null
      sector:
          action: attribute_not_null
          attr2set: attribution
    -> ATTRIBUTE_MANAGER_NG_3
Note: Utilisation de la valeur par défaut si pas de secteur
ATTRIBUTE_MANAGER_NG_3
    IN_YAML_TEXT:
      # Default value for sector if null
      sector:
          action: attribute_not_null
          attr2set: default_sector
    -> AttributeExposer_19
AttributeExposer_19
    ATTR_LIST = sector
    -> AttributeSplitter
Note: Séparation en/fr de l'attribut sector_temp avec le "/" comme séparateur.
AttributeSplitter
    ATTR_NAME = sector
    DELIMITER = /
    DROP_EMPTY_PARTS = No
    LIST_NAME = _list
    TRIM_OPTION = Both
    -> ATTRIBUTE_MANAGER_NG_4
Note: Définition du sector et sector_fr avec les 2 portilons de la liste
ATTRIBUTE_MANAGER_NG_4
    IN_YAML_TEXT:
      sector:
          action: attribute_overwrite
          attr2set: _list{0}

      sector_fr:
          action: attribute_overwrite
          attr2set: _list{1}
    -> ATTRIBUTE_MANAGER_NG_5
Note: Si pas de contenu français pour le secteur, on met l'anglais dans le fraçais
ATTRIBUTE_MANAGER_NG_5
    IN_YAML_TEXT:
      sector_fr:
          action: attribute_not_null
          attr2set: _list{0}
    -> AttributeExposer_20
AttributeExposer_20
    ATTR_LIST = _list{},resource.id
    -> AttributeRemover_9
AttributeRemover_9
    LIST_ATTRS = _list{}
    -> UNIQUE_ID_CREATOR
UNIQUE_ID_CREATOR
    UNIQUE_ATT = @Value(resource.id)
    -> SECTOR_MAPPER_NG

Bookmark: Date conversion
AttributeExposer_13
    ATTR_LIST = publicationDate,createdAt,viewLastModified
    -> DateTimeConverter
Note: Formats all date fields to ISO yyyy-mm-dd
DateTimeConverter
    DATETIME_ATTR = viewLastModified createdAt publicationDate
    IN_FORMAT = %s$
    OUT_FORMAT = %Y-%m-%d
    PASSTHROUGH = NO
    REPAIR_INPUT = YES
    TEST_INPUT = 1611946240
    -> ATTRIBUTE_MANAGER_NG
    <REJECTED> -> Error_Datetime (writer XLSXW_1)
Error_Datetime (writer XLSXW_1)
    attributes: publicationDate string(200), createdAt string(200), viewLastModified string(200), fme_rejection_code string(20)

Bookmark: Sector filtering (Drop federal dataset)
SECTOR_MAPPER_NG
    FEATURE_TYPE = Sector_NB
    IN_CSV_LOOKUP_TABLES_DIR = $(IN_CSV_LOOKUPTABLES_DIR)
    P-T_ABBR = $(P-T_ABBR)
    PUBLISHED_OUTPUT -> AttributeExposer_18
    UNMAPPED_OUTPUT -> SECTOR_NB_missing_sector (writer XLSXW_1)
AttributeExposer_18
    ATTR_LIST = resource.id,name,description
    -> Tester_3
Note: Supprimer les datasets : / - Map viewer du NB (ksan-r62m) / - Federal Electoral Districts / Circonscriptions électorales fédérales (dgwg-z6d7)
Tester_3
    BOOL_OP = COMPOSITE
    COMPOSITE_TEST = 1 AND 2
    TEST_CLAUSE:
      TEST @Value(resource.id) != ksan-r62m
      TEST @Value(resource.id) != dgwg-z6d7
    TEST_MODE = TEST
    PASSED -> NB_FrenchEnglishAttributeSeparator_NG [Feature_Input]
    FAILED -> Logger
Logger
    LOG_FEATURE = LOG_ONLY
    MAXCOORDS = 20
    MAXFEATS = 20
    MESSAGE = @Value(name) dataset with id value @Value(resource.id) has been succesfully discarded.
    SEVERITY = INFO
SECTOR_NB_missing_sector (writer XLSXW_1)
    attributes: Socrata_id string(20), link string(20), description string(20), datetime string(20)

Bookmark: Gestion des champs bilingues pour distinguer le contenu FR versus EN
Note: Description to Notes
NB_FrenchEnglishAttributeSeparator_NG
    ATTRIBUTE_TO_SPLIT = description
    FEATURE_TYPE = NB_SlashCountSeparatorForDesc
    IN_CSV_LOOKUP_TABLES_DIR = $(IN_CSV_LOOKUPTABLES_DIR)
    P-T_ABBR = $(P-T_ABBR)
    Feature_Output -> AttributeRenamer
    MULTIPLE_UNCAUGHT_SLASH_IN_ATT -> NB_MULTIPLE_SLASH_IN_DESCRIPTION (writer XLSXW_1)
AttributeRenamer
    ATTR_TABLE:
      RENAME_SET_DEFAULT splited_attr_en > notes
      RENAME_SET_DEFAULT splited_attr_fr > notes_fr
    -> NB_FrenchEnglishAttributeSeparator_NG_2 [Feature_Input]
Note: Name to Title
NB_FrenchEnglishAttributeSeparator_NG_2
    ATTRIBUTE_TO_SPLIT = name
    FEATURE_TYPE = NB_SlashCountSeparatorForName
    IN_CSV_LOOKUP_TABLES_DIR = $(IN_CSV_LOOKUPTABLES_DIR)
    P-T_ABBR = $(P-T_ABBR)
    Feature_Output -> AttributeRenamer_2
    MULTIPLE_UNCAUGHT_SLASH_IN_ATT -> NB_MULTIPLE_SLASH_IN_NAME (writer XLSXW_1)
AttributeRenamer_2
    ATTR_TABLE:
      RENAME_SET_DEFAULT splited_attr_en > title
      RENAME_SET_DEFAULT splited_attr_fr > title_fr
    -> AttributeExposer_12
AttributeExposer
    ATTR_LIST = resource.id
    -> GEOPORTAL_WEBLINK_ADDER_NG
NB_MULTIPLE_SLASH_IN_NAME (writer XLSXW_1)
    attributes: Socrata_id string(20), link string(20), description string(20), datetime string(20)
NB_MULTIPLE_SLASH_IN_DESCRIPTION (writer XLSXW_1)
    attributes: Socrata_id string(20), link string(20), description string(20), datetime string(20)

Bookmark: transforming tags{} as tags{}.display_name
AttributeExposer_12
    ATTR_LIST = tags{}
    -> PythonCaller_6
PythonCaller_6
    PYTHONSOURCE:
      import fme
      import fmeobjects
      from Python.FME_utils import FME_utils

      # Template Function interface:
      # When using this function, make sure its name is set as the value of
      # the 'Class or Function to Process Features' transformer parameter
      def FeatureProcessor(feature):
          i=0

          max_index=FME_utils.max_index_attribute_list(feature,'tags{}')
          for j in range(max_index+1):
              feature.setAttribute('tags{%i}.display_name'%(i),feature.getAttribute('tags{%i}'%(j)))
              i=i+1
    PYTHONSYMBOL = FeatureProcessor
    -> ATTRIBUTE_UNEXPOSER_2
ATTRIBUTE_UNEXPOSER_2
    -> AttributeExposer

Bookmark: Création de la liste des ressources pour les jeux de données
Note: Création de la liste resources
GEOPORTAL_WEBLINK_ADDER_NG
    FEATURE_TYPE = GeoportalWeblink_NB
    IN_CSV_LOOKUP_TABLES_DIR = $(IN_CSV_LOOKUPTABLES_DIR)
    P-T_ABBR = $(P-T_ABBR)
    URL_VALIDATION = $(URL_VALIDATION)
    WEBLINK_WILDCARD = @Value(resource.id)
    -> SOCRATA_ADDITIONAL_ACCESS_POINTS_RESOURCES_EXTRACTOR
Note: Extraction des ressources dans additional access points / Crée la liste / additional_access_points_resources
SOCRATA_ADDITIONAL_ACCESS_POINTS_RESOURCES_EXTRACTOR
    -> SOCRATA_ATTACHEMENTS_EXTRACTOR
Note: Extraction des resources dans les attachements / Crée la liste attachement_resources
SOCRATA_ATTACHEMENTS_EXTRACTOR
    SBN_URL_ROOT = https://gnb.socrata.com
    URL_VALIDATION = $(URL_VALIDATION)
    -> SOCRATA_ADVANCED_VIEW_EXTRACTOR
Note: Extraction des ressources dans les vues avanacées / Crée la liste advancedview_resources
SOCRATA_ADVANCED_VIEW_EXTRACTOR
    -> SOCRATA_INSIDE_DB_EXTRACTOR_NG
SOCRATA_INSIDE_DB_EXTRACTOR_NG
    DOMAIN = https://gnb.socrata.com
    Field_datatype = NB_FieldType_NG
    Field_name = NB_GeoDataFieldName
    IN_CSV_LOOKUP_TABLES_DIR = $(IN_CSV_LOOKUPTABLES_DIR)
    LinkBuilderNonGeo = NB_LINKBUILDER_NONGEO
    P-T_ABBR = $(P-T_ABBR)
    URL_VALIDATION = $(URL_VALIDATION)
    linkbuilder_geo = NB_LINKBUILDER_GEO
    -> AttributeExposer_5
URL_HTTPS_MAKER
    URL_VALIDATION = Yes
    -> EMPTY_FORMAT_MAPPER_NG [DATA_INPUT]
Note: Extraction du format
EMPTY_FORMAT_MAPPER_NG
    CSV_FORMAT = Format
    CSV_MIME_TYPE = Mime_type
    IN_CSV_LOOKUP_TABLES_DIR = $(IN_CSV_LOOKUPTABLES_DIR)
    P-T_ABBR = $(P-T_ABBR)
    URL_VALIDATION = $(URL_VALIDATION)
    DATA_OUTPUT -> AttributeExposer_7

Bookmark: Fusion des listes de resources dans une seule liste
AttributeExposer_5
    ATTR_LIST = resources{}.url,resources_copy{},socrata_db_resources{},advancedview_resources{},additional_access_points_resources{},attachement_resources{}
    -> ListCopier
ListCopier
    DEST_LIST = resources_copy
    SRC_LIST = resources{}
    -> AttributeRemover
AttributeRemover
    LIST_ATTRS = resources{}
    -> PythonCaller_3
PythonCaller_3
    NEW_ATTRIBUTES = resources{}.name resources{}.url resources{}.format resources{}.name_fr
    PYTHONSOURCE:
      import fme
      import fmeobjects
      logger = fmeobjects.FMELogFile()
      # Template Function interface:
      # When using this function, make sure its name is set as the value of
      # the 'Class or Function to Process Features' transformer parameter
      def processFeature(feature):
          list_list_name=[r'resources_copy',r'socrata_db_resources',r'advancedview_resources',r'additional_access_points_resources',r'attachement_resources']
          list_attr_name=[r'format',r'url',r'name',r'name_fr',r'spatial_type']

          i=0





          for list_name in list_list_name:

              #Extracting number of resources
              list_url=feature.getAttribute('%s{}.url'%(list_name))
              if list_url:
                  #Looping in resources
                  for j in range(len(list_url)):
                      #Looping in attributes
                      for attr_name in list_attr_name:
                          feature.setAttribute('resources{%i}.%s'%(i,attr_name),feature.getAttribute('%s{%i}.%s'%(list_name,j,attr_name)))

                      #Changing index feature where new features
                      i=i+1
    PYTHONSYMBOL = processFeature
    -> ListDuplicateRemover_2
Note: Removing dupplicates on URL
ListDuplicateRemover_2
    SRC_LIST = resources{}.url
    -> AttributeRemover_7
AttributeRemover_7
    LIST_ATTRS = socrata_db_resources{} resources_copy{} advancedview_resources{} additional_access_points_resources{} attachement_resources{}
    -> URL_HTTPS_MAKER [UUIDGenerator_Input]

Bookmark: Création d'une liste avec les catégories pour pouvoir fouiller dedans avec le Geospatial data validator
AttributeExposer_7
    ATTR_LIST = category
    -> AttributeCreator_6
AttributeCreator_6
    ATTR_TABLE = SET_TO category{0}.value = @LowerCase(@Value(category))
    -> GEO_NONE_GEO_SELECTOR

Bookmark: Filtrage geo / non-geo
GEO_NONE_GEO_SELECTOR
    CSV_FILE_NAME = GeospatialValidation
    CSV_PATH = $(IN_CSV_LOOKUPTABLES_DIR)
    CSV_PROVINCE = $(P-T_ABBR)
    YAML_DIRECTIVES:
      resources{}.format:
        domain: lookup_table_format
        spatial_type: if_null_overwrite
        not_found: log
        search_type: equals
      #
      category{}.value:
        domain: [lidar, geographic]
        spatial_type: no_overwrite
        not_found: no_log
        search_type: contains
    GEOSPATIAL -> AttributeExposer_8
    NONE_GEOSPATIAL -> AttributeExposer_9
    LOG_ERROR -> unknown_format (writer XLSXW_1)
AttributeExposer_8
    ATTR_LIST = category{}
    -> AttributeRemover_3
Note: Suppression de la liste temporaire
AttributeRemover_3
    LIST_ATTRS = category{}
    -> AttributeExposer_4
AttributeExposer_22
    ATTR_LIST = id,id_temp
    -> AttributeManager
AttributeManager
    ATTR_TABLE:
      SET_TO id = @Value(id_temp)
      REMOVE id_temp
    -> AttributeCreator_13
unknown_format (writer XLSXW_1)
    attributes: id string(20), _not_found_err_msg string(20), format string(20), _timestamp string(20)
AttributeExposer_9
    ATTR_LIST = category{}
    -> AttributeRemover_4
Note: Suppression de la liste temporaire
AttributeRemover_4
    LIST_ATTRS = category{}
    -> MANUAL_GEOSPATIAL_SETTER_NG [DATA_INPUT]
MANUAL_GEOSPATIAL_SETTER_NG
    FEATURE_TYPE = UnmappedGeoData_NB
    IN_CSV_LOOKUP_TABLES_DIR = $(IN_CSV_LOOKUPTABLES_DIR)
    P-T_ABBR = $(P-T_ABBR)
    GEOSPATIAL -> AttributeCreator_13
    NON-GEOSPATIAL -> AttributeCreator_14
    UNMAPPED_DATA -> unknow_geo_non_geo (writer XLSXW_1)
Note: _typedataset = GEO
AttributeCreator_13
    ATTR_TABLE = SET_TO _typedataset = GEO
    -> TestFilter
Note: _typedataset = NONGEO
AttributeCreator_14
    ATTR_TABLE = SET_TO _typedataset = NONGEO
    -> TestFilter_2
unknow_geo_non_geo (writer XLSXW_1)
    attributes: id string(200), notes string(200), title string(200), url string(200)

Bookmark: Adding spatial type manually
AttributeExposer_4
    ATTR_LIST = id,resource.id
    -> AttributeCreator_3
AttributeCreator_3
    ATTR_TABLE = SET_TO id_temp = @Value(id)
    -> AttributeCreator_4
AttributeCreator_4
    ATTR_TABLE = SET_TO id = @Value(resource.id)
    -> SPATIAL_TYPE_MAPPER_NG [DATA_INPUT]
SPATIAL_TYPE_MAPPER_NG
    FEATURE_TYPE = SpatialType_NB
    IN_CSV_LOOKUP_TABLES_DIR = $(IN_CSV_LOOKUPTABLES_DIR)
    P-T_ABBR = $(P-T_ABBR)
    DATA_OUTPUT_PASSED -> AttributeExposer_22

Bookmark: Samples or full content
TestFilter_3
    DEFAULT_VALUE = SAMPLES FEATURES
    TEST_LIST = "BOOL_OP,OR,COMPOSITE_TEST,""""""1"""""",TEST_CLAUSE,TEST $(SAMPLE_SIZE) = 0",ALL FEATURES
    ALL FEATURES -> Junction
    SAMPLES FEATURES -> Sampler
Sampler
    RATE = $(SAMPLE_SIZE)
    SAMPLE_MODE = No
    SAMPLE_TYPE_LONG = First N Features
    SAMPLED -> Junction

Bookmark: Metadata Value Mapping
Note: Topic
METADATA_VALUE_MAPPER_NG
    ATT_TO_MAP = category
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_2 [DATA_INPUT]
Note: Role
METADATA_VALUE_MAPPER_NG_2
    ATT_TO_MAP = contacts{}.role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_3 [DATA_INPUT]
Note: Update
METADATA_VALUE_MAPPER_NG_3
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: Progress
METADATA_VALUE_MAPPER_NG_4
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: SpatialRepresentation
METADATA_VALUE_MAPPER_NG_5
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> ATTRIBUTE_MAPPING_ERRORS (writer XLSXW_1)
    DATA_OUTPUT -> AttributeRemover_6
ATTRIBUTE_MAPPING_ERRORS (writer XLSXW_1)
    attributes: error string(200), id string(200), _element_index string(200)
Note: Removing error list
AttributeRemover_6
    LIST_ATTRS = mapping_errors{}
    -> RESOURCE_NAME_UNDERSCORE_REMOVER

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    URL_VALIDATION = Yes
    -> WMS_REST_LANGUAGE_FORMATTER
    FAULTY_URL_OUTPUT -> MAP_SERVICE_URL_ERRORMAP (writer XLSXW_1)
MAP_SERVICE_URL_ERRORMAP (writer XLSXW_1)
    attributes: id string(200), url string(200), format string(200), _url_failure_message string(200)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> AttributeCreator

Bookmark: Configuring publishing info
AttributeCreator
    ATTR_TABLE = SET_TO csw_url = $(FORCED_PYCSW_URL)
    -> AttributeExposer_2
AttributeExposer_2
    ATTR_LIST = search_criteria_pycsw
    -> METADATA_DELTA_FINDER_NG
Note: Searches existing PyCSW for new, updated or obsolete data
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> StatisticsCalculator_Summary
    No_Change -> Junction_4
    Update -> Junction_4
    Insert -> Junction_4
    Delete -> DELETEDRECORDS (writer XLSXW_1)
StatisticsCalculator_Summary: Logger
    LOG_FEATURE = NONE
    MAXFEATS = 20
    MESSAGE:
      ************************
      **** Unchanged Report ****
      ************************

      @Value(_real_count) features were unchanged

      ************************
      ************************
      ************************
    SEVERITY = INFO
Junction_4
    -> AWS_TRANSLATE_6
DELETEDRECORDS (writer XLSXW_1)

Bookmark: AWS Translation
Note: English to french / notes, / title, / tags_en / resources name
AWS_TRANSLATE_6
    ACTIVATE_TRANSLATION = $(ACTIVATE_TRANSLATION)
    ATTR_2_TRANSLATE = notes,title
    ATTR_LIST_2_TRANSLATE = resources{}.name,tags{}.display_name
    MODE = English-->French
    -> AttributeExposer_15
    TRANSLATION_PROBLEM -> Translation_errors01 (writer XLSXW_1)
Translation_errors01 (writer XLSXW_1)
    attributes: id string(20), _timestamp string(20)

Bookmark: Rebuilding tags list
AttributeExposer_15
    ATTR_LIST = tags{}.display_name_en,tags{}.display_name_fr
    -> PythonCaller_5
PythonCaller_5
    PYTHONSOURCE:
      import fme
      import fmeobjects
      from Python.FME_utils import FME_utils

      # Template Function interface:
      # When using this function, make sure its name is set as the value of
      # the 'Class or Function to Process Features' transformer parameter
      def FeatureProcessor(feature):
          i=0

          max_index_en=FME_utils.max_index_attribute_list(feature,'tags{}.display_name_en')
          for j in range(max_index_en+1):
              feature.setAttribute('tags{%i}.display_name_en_lower'%(i),feature.getAttribute('tags{%i}.display_name_en'%(j)).lower())
              feature.setAttribute('tags{%i}.display_name_fr_lower'%(i),feature.getAttribute('tags{%i}.display_name_fr'%(j)).lower())
              i=i+1
    PYTHONSYMBOL = FeatureProcessor
    -> AttributeExposer_21
AttributeExposer_21
    ATTR_LIST = tags{}.display_name_en_lower,tags{}.display_name_fr_lower
    -> ListDuplicateRemover_5
ListDuplicateRemover_5
    SRC_LIST = tags{}.display_name_en_lower
    -> ListDuplicateRemover_6
ListDuplicateRemover_6
    SRC_LIST = tags{}.display_name_fr_lower
    -> ATTRIBUTE_UNEXPOSER
ATTRIBUTE_UNEXPOSER
    -> XML_PUBLISHER_NG

Bookmark: XML CREATION AND WRITING
XML_PUBLISHER_NG
    FEATURE_TYPE = Config_NB
    IN_CSV_LOOKUP_TABLES_DIR = $(IN_CSV_LOOKUPTABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> invalid_metadata (writer XLSXW_1)
    UPDATE_FAILED -> text_line (writer TEXTLINE_2)

Bookmark: Samples or full content
TestFilter_4
    DEFAULT_VALUE = SAMPLES FEATURES
    TEST_LIST = "BOOL_OP,OR,COMPOSITE_TEST,""""""1"""""",TEST_CLAUSE,TEST $(SAMPLE_SIZE) = 0",ALL FEATURES
    ALL FEATURES -> Junction_2
    SAMPLES FEATURES -> Sampler_2
Sampler_2
    RATE = $(SAMPLE_SIZE)
    SAMPLE_MODE = No
    SAMPLE_TYPE_LONG = First N Features
    SAMPLED -> Junction_2

Bookmark: Metadata Value Mapping - NONGEO
Note: Gestion des attributs
ATTRIBUTE_MANAGER_NG_6
    IN_YAML_TEXT:
      # Create a new tbs_topic attribute
      tbs_topic:
          action: attribute_overwrite
          attr2set: category

      # Create a new tbs_subject attribute
      tbs_subject:
          action: attribute_overwrite
          attr2set: category
    -> METADATA_VALUE_MAPPER_NG_6 [DATA_INPUT]
Note: UpdateFrequency_TBS
METADATA_VALUE_MAPPER_NG_8
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUPTABLES_DIR)
    P-T_ABBR = $(P-T_ABBR)
    -> METADATA_FORMAT_MAPPER_NG_2 [DATA_INPUT]
Note: Format_TBS
METADATA_FORMAT_MAPPER_NG_2
    ATT_TO_MAP = resources{}.format
    ERROR_NOT_MAPPED = YES
    FEATURE_TYPE = Format_TBS
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_ERROR_MANAGER_2
METADATA_VALUE_MAPPER_ERROR_MANAGER_2
    ERROR_OUTPUT -> ATTRIBUTE_MAPPING_ERRORS00_NONGEO (writer XLSXW_1)
    DATA_OUTPUT -> AttributeExposer_16
ATTRIBUTE_MAPPING_ERRORS00_NONGEO (writer XLSXW_1)
    attributes: error string(200), id string(200), _element_index string(200)

Bookmark: Generating Tbs Topic based on category
Note: Topic_TBS
METADATA_VALUE_MAPPER_NG_6
    ATT_TO_MAP = tbs_topic
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUPTABLES_DIR)
    P-T_ABBR = $(P-T_ABBR)
    -> METADATA_VALUE_MAPPER_NG_7 [DATA_INPUT]

Bookmark: Generating TBS_SUBJECT list based on category
Note: Subject_TBS
METADATA_VALUE_MAPPER_NG_7
    ATT_TO_MAP = tbs_subject
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUPTABLES_DIR)
    P-T_ABBR = $(P-T_ABBR)
    -> AttributeExposer_10
AttributeExposer_10
    ATTR_LIST = TBS_Subject{}.value
    -> METADATA_VALUE_MAPPER_NG_8 [DATA_INPUT]

Bookmark: Default value for resources language
AttributeExposer_16
    ATTR_LIST = resources{},default_res_language
    -> ListElementCounter
ListElementCounter
    CNT_ATTR = _element_count
    LIST_NAME = resources{}
    -> PythonCaller
PythonCaller
    PYTHONSOURCE:
      import fme
      import fmeobjects
      # Template Class Interface:
      # When using this class, make sure its name is set as the value of
      # the 'Class or Function to Process Features' transformer parameter
      def FeatureProcessor(feature):
          split_list = str(feature.getAttribute('default_resource_language')).split(";")
          resource_language = '['

          for i in range(len(split_list)):
              if i == len(split_list) - 1:
                  resource_language = resource_language + '"' + split_list[i] + '"'
              else:
                  resource_language = resource_language + '"' + split_list[i] + '",'

          resource_language = resource_language + ']'

          for i in range(int(feature.getAttribute('_element_count'))):
              feature.setAttribute('resources{%d}.language_list'%(i),str(resource_language))
    PYTHONSYMBOL = FeatureProcessor
    -> AttributeRemover_10
AttributeRemover_10
    REMOVE_ATTRS = _element_count
    -> METADATA_DELTA_FINDER_NG_2

Bookmark: Delta Finder -NONGEO
Note: Searches existing PyCSW for new, updated or obsolete data
METADATA_DELTA_FINDER_NG_2
    ABSTRACT_ATT_NEW = notes
    ABSTRACT_ATT_REF = notes_translated.en
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    METADATA_OVERWRITE = YES
    RES_FORMAT_ATT_NEW = resources{}.format
    RES_FORMAT_ATT_REF = resources{}.format
    RES_NAME_ATT_NEW = resources{}.name
    RES_NAME_ATT_REF = resources{}.name_translated.en
    RES_URL_ATT_NEW = resources{}.url
    RES_URL_ATT_REF = resources{}.url
    TITLE_ATT_NEW = title
    TITLE_ATT_REF = title_translated.en
    Statistics -> StatisticsCalculator_Summary_3
    Update -> Junction_3
    Insert -> Junction_3
    Delete -> DELETED_RECORDS_NONE_GEO00 (writer XLSXW_1)
Note: Log statistics
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
Junction_3
    -> AWS_TRANSLATE_2
Note: Log deleted features
DELETED_RECORDS_NONE_GEO00 (writer XLSXW_1)
    attributes: id auto(20)

Bookmark: AWS Translation
Note: English to french / notes, / title, / tags_en / resources name
AWS_TRANSLATE_2
    ACTIVATE_TRANSLATION = $(ACTIVATE_TRANSLATION)
    ATTR_2_TRANSLATE = notes,title
    ATTR_LIST_2_TRANSLATE = resources{}.name,tags{}.display_name
    MODE = English-->French
    -> AttributeExposer_6
    TRANSLATION_PROBLEM -> Translation_errors0100 (writer XLSXW_1)
Translation_errors0100 (writer XLSXW_1)
    attributes: id string(20), _timestamp string(20)

Bookmark: Rebuilding tags list
AttributeExposer_6
    ATTR_LIST = tags{}.display_name_en,tags{}.display_name_fr
    -> PythonCaller_2
PythonCaller_2
    PYTHONSOURCE:
      import fme
      import fmeobjects
      from Python.FME_utils import FME_utils

      # Template Function interface:
      # When using this function, make sure its name is set as the value of
      # the 'Class or Function to Process Features' transformer parameter
      def FeatureProcessor(feature):
          i=0

          max_index_en=FME_utils.max_index_attribute_list(feature,'tags{}.display_name_en')
          for j in range(max_index_en+1):
              feature.setAttribute('tags{%i}.display_name_en_lower'%(i),feature.getAttribute('tags{%i}.display_name_en'%(j)).lower())
              feature.setAttribute('tags{%i}.display_name_fr_lower'%(i),feature.getAttribute('tags{%i}.display_name_fr'%(j)).lower())
              i=i+1
    PYTHONSYMBOL = FeatureProcessor
    -> AttributeExposer_14
AttributeExposer_14
    ATTR_LIST = tags{}.display_name_en_lower,tags{}.display_name_fr_lower
    -> ListDuplicateRemover_3
ListDuplicateRemover_3
    SRC_LIST = tags{}.display_name_en_lower
    -> ListDuplicateRemover_4
ListDuplicateRemover_4
    SRC_LIST = tags{}.display_name_fr_lower
    -> ATTRIBUTE_UNEXPOSER_3
ATTRIBUTE_UNEXPOSER_3
    -> AttributeExposer_11

Bookmark: JSON CREATION AND WRITING
AttributeExposer_11
    ATTR_LIST = tbs_topic,tbs_subject
    -> AttributeCreator_7
AttributeCreator_7
    ATTR_TABLE:
      SET_TO TBS_Topic{0}.value = @Value(tbs_topic)
      SET_TO TBS_Subject{0}.value = @Value(tbs_subject)
    -> JSON_PUBLISHER_NG
Note: Config_JSON_NB
JSON_PUBLISHER_NG
    FEATURE_TYPE = Config_JSON_NB
    IN_CSV_LOOKUP_TABLES_DIR = $(IN_CSV_LOOKUPTABLES_DIR)
    JSON_RESOURCE_TEMPLATE = $(IN_TBS_JSON_TEMPLATE_DIR)/TBS_RESOURCES_TEMPLATE_NG.json
    JSON_ROOT_TEMPLATE = $(IN_TBS_JSON_TEMPLATE_DIR)/TBS_ROOT_TEMPLATE_NG.json
    Keywords_EN = tags{}.display_name
    Keywords_FR = tags{}.display_name_fr
    P-T_ABBR = $(P-T_ABBR)
    Subject_LIST = TBS_Subject{}.value
    Topic_LIST = TBS_Topic{}.value
    OUTPUT_LOCAL -> AttributeExposer_17
AttributeExposer_17
    ATTR_LIST = json_file
    -> text_line (writer TEXTLINE_4)
text_line (writer TEXTLINE_4)
    attributes: text_line_data buffer
