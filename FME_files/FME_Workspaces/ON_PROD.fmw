FME workspace ON_PROD.fmw
Title: ON_PROD
Description: Description 
This workbench read and trasform all the metadata for the province of Ontario (ON)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...). Extracted automatically using a Python script from the name of the FME Workspace (ex.: ON_PROD.fmw)
METADATA_OVERWRITE: Enable the overwite of the PyCSW.  Can take two values: Yes: Overwrite the content of the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: \ON\LOG\ON.log
OUT_JSON_LOCAL_DIR: Source directory to output JSON files. Defined as: \ON\JSON_LOCAL
OUT_XLS_NOTIFICATION: Source directory to output excel files. Defined as: \ON\XLS
OUT_XML_FAILED_DIR: Source directory to output failed XML files. Defined as: \ON\XML_FAILED
OUT_XML_LOCAL_DIR: Source directory to output Local Source XML files. Defined as: \ON\XML_LOCAL
OUT_XML_PASSED_DIR: Source directory to output passedXML files. Defined as: \ON\XML_PASSED
SAMPLE_SIZE: Number of features to process. Zero (0) means process all the features. A number n greater than 0 means sample or process only the first n features.
URL_VALIDATION : Indicates to validate or not created URL. (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- IN_OUT_WORKING_DIR = $(FME_SHAREDRESOURCE_DATA)\PT_Harvester
- SAMPLE_SIZE = 0
- URL_VALIDATION = Yes
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Resource Data

Writers:
- XLSXW_1: XLSXW to $(OUT_XLS_NOTIFICATION_DIR)
- TEXTLINE_1: TEXTLINE to $(OUT_JSON_LOCAL_DIR)
- TEXTLINE_2: TEXTLINE to $(OUT_XML_PASSED_DIR)
- TEXTLINE_3: TEXTLINE to $(OUT_XML_FAILED_DIR)
- TEXTLINE_4: TEXTLINE to $(OUT_XML_LOCAL_DIR)

AttributeExposer_7
    ATTR_LIST = license_id
    -> LICENSE_FILTER_NG
LICENSE_FILTER_NG
    FEATURE_TYPE = License_ON
    IN_CSV_LOOKUP_TABLES_DIR = $(IN_CSV_LOOKUP_TABLES_DIR)
    LICENSE_ATT = @Value(license_id)
    P-T_ABBR = $(P-T_ABBR)
    LICENSE_FILTER_PASSED -> SECTOR_MAPPER_NG
    UNKNOWN_LICENSE -> LICENSE_ID_NOT_MAPPED (writer XLSXW_1)
SECTOR_MAPPER_NG
    FEATURE_TYPE = Sector_ON
    IN_CSV_LOOKUP_TABLES_DIR = $(IN_CSV_LOOKUP_TABLES_DIR)
    P-T_ABBR = $(P-T_ABBR)
    PUBLISHED_OUTPUT -> AttributeExposer_18
    UNMAPPED_OUTPUT -> SECTOR_NOT_MAPPED (writer XLSXW_1)
Junction
    -> METADATA_VALUE_MAPPER_NG [DATA_INPUT]
Note: Writes XML to a local folder without publishing to PyCSW, and without the PyCSW transaction headers and footers
text_line (writer TEXTLINE_4)
    attributes: text_line_data buffer
Note: Writes XML published to the PyCSW to a local folder
text_line (writer TEXTLINE_2)
    attributes: text_line_data buffer
Note: Writes XML that failed to publish to the PyCSW to a local folder
text_line (writer TEXTLINE_3)
    attributes: text_line_data buffer
Junction_2
    -> AttributeExposer_2
text_line (writer TEXTLINE_1)
    attributes: text_line_data buffer
SECTOR_NOT_MAPPED (writer XLSXW_1)
    attributes: sector string(200), id string(200)
LICENSE_ID_NOT_MAPPED (writer XLSXW_1)
    attributes: license_id string(200), id string(200)

Bookmark: Reading ON Datasets and creating attributes
Creator
    GEOMTYPE = Geometry Object
    NUM = 1
    CREATED -> Tester_3
Tester_3
    BOOL_OP = OR
    COMPOSITE_TEST = 1
    TEST_CLAUSE = TEST $(CATALOGUE_READER_SELECT) = Yes
    TEST_MODE = TEST
    PASSED -> Catalogue_Reader
    FAILED -> FeatureReader [INITIATOR]
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> AttributeExposer_10
Catalogue_Reader: Catalogue Reader
    CUSTOM_CSW_LIST_NAME = DefaultNoList{}
    CUSTOM_URL = https://data.ontario.ca/en/api/3/action
    SOURCE_URL = Manuel
    Résultats -> ON_GEOHUB_RESOURCE_EXTRACTOR [DATA_INPUT]
Note: Geohub_ON_URL
LOOKUP_TABLES_READER
    CSV_ENCODING = utf-8
    CSV_PATH = $(IN_CSV_LOOKUP_TABLES_DIR)
    FEATURE_TYPE = Geohub_ON_URL
    PT = ON
    -> ON_GEOHUB_RESOURCE_EXTRACTOR [LOOKUP_TABLE_INPUT]
Note: Processes data found in ON Geohub, filters out broken geohub links and bypasses non-geohub data
ON_GEOHUB_RESOURCE_EXTRACTOR
    BROKEN_GEOHUB_URL -> BROKEN_GEOHUB_URL (writer XLSXW_1)
    GEOHUB_DATA_OUTPUT -> AttributeExposer_10
    NO_GEOHUB_LINK -> AttributeExposer_10
AttributeExposer_10
    ATTR_LIST = license_id,resources{}
    -> ListElementCounter_2
ATTRIBUTE_VALUE_TEXT_CLEANER_2
    -> DEFAULT_ATTRIBUTE_MAPPER_NG
Note: Sets default attribute values
DEFAULT_ATTRIBUTE_MAPPER_NG
    FEATURE_TYPE = Default_ON
    IN_CSV_LOOKUP_TABLES_DIR = $(IN_CSV_LOOKUP_TABLES_DIR)
    P-T_ABBR = $(P-T_ABBR)
    -> ON_CKAN_CONTACT_FORM_EXTRACTOR
Note: Extraction du formulaire de contact pour Ontario
ON_CKAN_CONTACT_FORM_EXTRACTOR
    CKAN_ROOT = https://data.ontario.ca
    URL_VALIDATION = $(URL_VALIDATION)
    -> ON_KEYWORD_RENAMER [DATA_INPUT]
ON_KEYWORD_RENAMER
    DATA_OUTPUT -> ATTRIBUTE_MANAGER_NG_3
ATTRIBUTE_MANAGER_NG_3
    IN_YAML_TEXT:
      sector:
         action: attribute_overwrite
         attr2set: organization.title
      record_create_date:
         action: attribute_overwrite
         attr2set: metadata_created
      record_last_modified:
         action: attribute_overwrite
         attr2set: metadata_modified
      title_fr:
         action: attribute_overwrite
         attr2set: title_translated.fr
      notes_fr:
         action: attribute_overwrite
         attr2set: notes_translated.fr
      record_publish_date:
         action: attribute_overwrite
         attr2set: metadata_created
      update_frequency:
         action: attribute_not_null
         attr2set: default_update_frequency
    -> ATTRIBUTE_MANAGER_NG_2
ATTRIBUTE_MANAGER_NG_2
    IN_YAML_TEXT:
      sector:
        action: attribute_not_null
        attr2set: default_sector
    -> EMPTY_FORMAT_MAPPER_NG [DATA_INPUT]
Note: When format is emty. Guess the format using the conent of the URL
EMPTY_FORMAT_MAPPER_NG
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> RESOURCES_VALIDATOR
    UNKNOWN_MIME_TYPE -> MIME_TYPE_NOT_MAPPED (writer XLSXW_1)
Note: Nettoie les ressources sans url
RESOURCES_VALIDATOR
    -> AttributeExposer_5
AttributeExposer_5
    ATTR_LIST = default_on_topic
    -> ON_TopicExtractor
Note: Extraction des vrais Topic de l'ontariio qui sont éparpillés dans les keywords / On se fie sur la liste des catégories disponibles sur la page d'accueil du portail / CT à arranger avec le nouveau lookup table reader. C'est pour ça qu'il est embeeded
ON_TopicExtractor
    DEFAULT_TOPIC = @Value(default_on_topic)
    FEATURE_TYPE = Topic_Topic_ON
    IN_CSV_LOOKUP_TABLES_DIR = $(IN_CSV_LOOKUP_TABLES_DIR)
    P-T_ABBR = $(P-T_ABBR)
    -> ON_DATE_FORMATTER
ON_DATE_FORMATTER
    -> AttributeExposer_7
MIME_TYPE_NOT_MAPPED (writer XLSXW_1)
    attributes: id string(200), _unknown_mime_type string(200)
BROKEN_GEOHUB_URL (writer XLSXW_1)
    attributes: id string(200), new_url string(200)

Bookmark: Filtrage des entités dans ressources
ListElementCounter_2
    CNT_ATTR = nb_res
    LIST_NAME = resources{}
    -> Tester
Tester
    BOOL_OP = OR
    COMPOSITE_TEST = 1
    TEST_CLAUSE = TEST @Value(nb_res) != 0
    TEST_MODE = TEST
    PASSED -> ATTRIBUTE_VALUE_TEXT_CLEANER_2

Bookmark: Add Geoportal Weblink
AttributeExposer_18
    ATTR_LIST = id
    -> GEOPORTAL_WEBLINK_ADDER_NG
Note: Ajout du lien vers la métadonnées en anglais
GEOPORTAL_WEBLINK_ADDER_NG
    FEATURE_TYPE = GeoportalWeblink_ON_en
    IN_CSV_LOOKUP_TABLES_DIR = $(IN_CSV_LOOKUP_TABLES_DIR)
    P-T_ABBR = $(P-T_ABBR)
    URL_VALIDATION = $(URL_VALIDATION)
    WEBLINK_WILDCARD = @Value(id)
    -> AttributeExposer_19
AttributeExposer_19
    ATTR_LIST = id
    -> GEOPORTAL_WEBLINK_ADDER_NG_2
Note: Ajout du lien vers la métadonnées en français
GEOPORTAL_WEBLINK_ADDER_NG_2
    FEATURE_TYPE = GeoportalWeblink_ON_fr
    IN_CSV_LOOKUP_TABLES_DIR = $(IN_CSV_LOOKUP_TABLES_DIR)
    P-T_ABBR = $(P-T_ABBR)
    URL_VALIDATION = $(URL_VALIDATION)
    WEBLINK_WILDCARD = @Value(id)
    -> AttributeExposer_11
AttributeExposer_11
    ATTR_LIST = resources{}
    -> ListElementCounter
ListElementCounter
    CNT_ATTR = _element_count
    LIST_NAME = resources{}
    -> PythonCaller_3
Note: Cération de lang_list / pour la sortie pour TBS
PythonCaller_3
    PYTHONSOURCE:
      import fme
      import fmeobjects
      # Template Function interface:
      # When using this function, make sure its name is set as the value of
      # the 'Class or Function to Process Features' transformer parameter
      def processFeature(feature):
          for i in range(int(feature.getAttribute('_element_count'))):
              langue=feature.getAttribute('resources{%i}.language'%(i))
              if not langue:
                  langue='english'
              feature.setAttribute('resources{%i}.language'%(i),langue)
              feature.setAttribute('resources{%i}.language_list'%(i),langue)
    PYTHONSYMBOL = processFeature
    -> GEO_NONE_GEO_SELECTOR

Bookmark: Spatail data filtering
Note: Filters geospatial data by referencing format, then by resources identified as having geographic markers
GEO_NONE_GEO_SELECTOR
    CSV_FILE_NAME = GeoSpatialValidation
    CSV_PATH = $(IN_CSV_LOOKUP_TABLES_DIR)
    CSV_PROVINCE = $(P-T_ABBR)
    YAML_DIRECTIVES:
      resources{}.format:
        domain: lookup_table_format
        spatial_type: overwrite
        not_found: log
        search_type: equals
      #
      resources{}.contains_geographic_markers:
        domain: ["Yes","yes"]
        spatial_type: no_overwrite
        not_found: no_log
        search_type: contains
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: Maps the spatial_representation_type of known geographic data, and geo data that could not be mapped to a specific spatial_representation_type is given value through lookup table where the type was researched manually
SPATIAL_TYPE_MAPPER_NG
    FEATURE_TYPE = UUID_Spatial_ON
    IN_CSV_LOOKUP_TABLES_DIR = $(IN_CSV_LOOKUP_TABLES_DIR)
    P-T_ABBR = $(P-T_ABBR)
    DATA_OUTPUT_FAILED -> SPATIAL_TYPE_NOT_MAPPED (writer XLSXW_1)
    DATA_OUTPUT_PASSED -> Junction_3
SPATIAL_TYPE_NOT_MAPPED (writer XLSXW_1)
GEOSPATIAL_FORMAT_NOT_MAPPED (writer XLSXW_1)
    attributes: resources__ string(200), _element_count string(200), _geo_none_geo_status string(200), id string(200), _not_found_err_msg string(200), format string(200)
Note: Additional filtering step required for ON data. Items identified as NON-GEOSPATIAL in GEOSPATIAL_DATA_VALIDATOR were analyzed manually and a lookup table was created to identify non-filtered geo data and create the spatial_representation_type
MANUAL_GEOSPATIAL_SETTER_NG
    FEATURE_TYPE = UnmappedGeoData_ON
    IN_CSV_LOOKUP_TABLES_DIR = $(IN_CSV_LOOKUP_TABLES_DIR)
    P-T_ABBR = $(P-T_ABBR)
    GEOSPATIAL -> Junction_3
    NON-GEOSPATIAL -> Tester_2
    UNMAPPED_DATA -> UNMAPPED_GEODATA_ON (writer XLSXW_1)
Junction_3
    -> Tester_7
UNMAPPED_GEODATA_ON (writer XLSXW_1)
    attributes: id string(200), notes string(200), title string(200), url string(200)

Bookmark: Activate Geo and Sample or full content
Tester_7
    BOOL_OP = OR
    COMPOSITE_TEST = 1
    TEST_CLAUSE = TEST @UpperCase($(ACTIVATE_GEO)) = YES
    TEST_MODE = TEST
    PASSED -> TestFilter
TestFilter
    DEFAULT_VALUE = SAMPLES FEATURES
    TEST_LIST = "BOOL_OP,OR,COMPOSITE_TEST,""""""1"""""",TEST_CLAUSE,TEST $(SAMPLE_SIZE) = 0",ALL FEATURES
    ALL FEATURES -> Junction
    SAMPLES FEATURES -> Sampler_3
Sampler_3
    RATE = $(SAMPLE_SIZE)
    SAMPLE_MODE = No
    SAMPLE_TYPE_LONG = First N Features
    SAMPLED -> Junction

Bookmark: Attribute value mapper
METADATA_VALUE_MAPPER_NG
    ATT_TO_MAP = resources{}.language
    CODE_REFRESH = NO
    ENGLISH_REFRESH = YES
    ERROR_NOT_MAPPED = YES
    FEATURE_TYPE = TransferLang_ON
    FRENCH_REFRESH = NO
    IN_CSV_LOOKUP_TABLES_DIR = $(IN_CSV_LOOKUP_TABLES_DIR)
    P-T_ABBR = $(P-T_ABBR)
    -> METADATA_VALUE_MAPPER_NG_3 [DATA_INPUT]
Note: Map Role to HNAP standards
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
METADATA_VALUE_MAPPER_NG_3
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: Maps update cycle to HNAP standards
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: Maps progress code to HNAP standards
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_6 [DATA_INPUT]
Note: Maps spatial rpresentation to HNAP standards
METADATA_VALUE_MAPPER_NG_6
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_7 [DATA_INPUT]
Note: Maps spatial_representation_type to HNAP standards8
METADATA_VALUE_MAPPER_NG_7
    ATT_TO_MAP = extracted_topic{}.value
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_FORMAT_MAPPER_NG [DATA_INPUT]

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_VALUE_MAPPER_ERROR_MANAGER_2

Bookmark: Mapping error list creator
METADATA_VALUE_MAPPER_ERROR_MANAGER_2
    ERROR_OUTPUT -> ATTRIBUTE_MAPPING_ERRORS_GEO (writer XLSXW_1)
    DATA_OUTPUT -> REMOVE_BROKEN_URL_WMS_ESRI_REST
ATTRIBUTE_MAPPING_ERRORS_GEO (writer XLSXW_1)
    attributes: error string(200), id string(200), _element_index string(200)

Bookmark: Data cleanup. Dropping broken web services
Note: Tests WMS/ESRI_REST resource URL's and removes them where broken
REMOVE_BROKEN_URL_WMS_ESRI_REST
    URL_VALIDATION = $(URL_VALIDATION)
    -> WMS_REST_LANGUAGE_FORMATTER
    FAULTY_URL_OUTPUT -> MAP_SERVICE_URL_ERROR (writer XLSXW_1)
MAP_SERVICE_URL_ERROR (writer XLSXW_1)
    attributes: id auto(20), format string(8), url auto(20), _url_failure_message auto(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> AttributeExposer_13
AttributeExposer_13
    ATTR_LIST = resources{}
    -> ListCopier
ListCopier
    DEST_LIST = distributionList
    SRC_LIST = resources{}
    -> GMD_SECTION_DATA_EXTRACTION
Note: Creates lists and removes duplicates for GMD_Section
GMD_SECTION_DATA_EXTRACTION
    -> AttributeCreator

Bookmark: New Bookmark
AttributeCreator
    ATTR_TABLE = SET_TO csw_url = $(FORCED_PYCSW_URL)
    -> AttributeExposer_6
AttributeExposer_6
    ATTR_LIST = search_criteria_pycsw,csw_url
    -> METADATA_DELTA_FINDER_NG
Note: Searches existing PyCSW for new, updated or obsolete dat
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> StatisticsCalculator_Summary
    Update -> Junction_5
    Insert -> Junction_5
Note: Log statistics
StatisticsCalculator_Summary: Logger
    LOG_FEATURE = NONE
    MAXFEATS = 20
    MESSAGE:
      ************************
      **** Geo Unchanged Report ****
      ************************

      @Value(_real_count) features were unchanged

      ************************
      ************************
      ************************
    SEVERITY = INFO
Junction_5
    -> AWS_TRANSLATE

Bookmark: Language Translation
Note: Translate geo features
AWS_TRANSLATE
    ACTIVATE_TRANSLATION = $(ACTIVATE_TRANSLATION)
    ATTR_2_TRANSLATE = notes,title
    ATTR_LIST_2_TRANSLATE = tags{}.display_name,resources{}.name
    MODE = English-->French
    -> XML_PUBLISHER_NG
    TRANSLATION_PROBLEM -> TRANSLATION_PROBLEM_GEO (writer XLSXW_1)
TRANSLATION_PROBLEM_GEO (writer XLSXW_1)
    attributes: _aws_activation string(200), _mode string(200), _attr2translate string(200), _attrlist2translate string(200), _translation_status string(200)

Bookmark: XML CREATION AND WRITING
Note: Excel config file to map ON attributes to those required by XML templates
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER_NG
    FEATURE_TYPE = Config_ON
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_4)
    INSERT_PASSED -> text_line (writer TEXTLINE_2)
    UPDATE_PASSED -> text_line (writer TEXTLINE_2)
    INSERT_FAILED -> text_line (writer TEXTLINE_3)
    UPDATE_FAILED -> text_line (writer TEXTLINE_3)

Bookmark: Activate None Geo and Sample or fulle content
Tester_2
    BOOL_OP = OR
    COMPOSITE_TEST = 1
    TEST_CLAUSE = TEST @UpperCase($(ACTIVATE_NON_GEO)) = YES
    TEST_MODE = TEST
    PASSED -> TestFilter_2
TestFilter_2
    DEFAULT_VALUE = SAMPLES FEATURES
    TEST_LIST = "BOOL_OP,OR,COMPOSITE_TEST,""""""1"""""",TEST_CLAUSE,TEST $(SAMPLE_SIZE) = 0",ALL FEATURES
    ALL FEATURES -> Junction_2
    SAMPLES FEATURES -> Sampler_4
Sampler_4
    RATE = $(SAMPLE_SIZE)
    SAMPLE_MODE = No
    SAMPLE_TYPE_LONG = First N Features
    SAMPLED -> Junction_2

Bookmark: Non-Geospatial Export
AttributeExposer_2
    ATTR_LIST = author,author_email,groups{}.name,id,license_id,metadata_created,metadata_modified,notes,organization.title,resources{}.id,resources{}.name,resources{}.url,tags{}.display_name,temporal,title,update_frequency
    -> METADATA_VALUE_MAPPER_NG_2 [DATA_INPUT]
Note: Ajustement pour la langue des ressources
METADATA_VALUE_MAPPER_NG_2
    ATT_TO_MAP = resources{}.language_list
    CODE_REFRESH = NO
    ENGLISH_REFRESH = YES
    ERROR_NOT_MAPPED = YES
    FEATURE_TYPE = TransferLang_ON_TBS
    FRENCH_REFRESH = NO
    IN_CSV_LOOKUP_TABLES_DIR = $(IN_CSV_LOOKUP_TABLES_DIR)
    P-T_ABBR = $(P-T_ABBR)
    -> METADATA_VALUE_MAPPER_NG_8 [DATA_INPUT]
Note: Adjusting update frequency value
METADATA_VALUE_MAPPER_NG_8
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_2 [DATA_INPUT]
Note: Format TBS
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> AttributeExposer_9
METADATA_VALUE_MAPPER_ERROR_MANAGER
    ERROR_OUTPUT -> ATTRIBUTE_MAPPING_ERRORS_NON_GEO (writer XLSXW_1)
    DATA_OUTPUT -> RESOURCE_NAME_UNDERSCORE_REMOVER_2
Note: Removes all underscores from resources{}.name attributes. Long compounded names joined by underscores in this field can cause display formatting issues when published to the FGP.
RESOURCE_NAME_UNDERSCORE_REMOVER_2
    DATA_OUTPUT -> METADATA_DELTA_FINDER_NG_2
Note: Searches existing PyCSW for new, updated or obsolete dat
METADATA_DELTA_FINDER_NG_2
    ABSTRACT_ATT_NEW = notes
    ABSTRACT_ATT_REF = notes_translated.en
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    METADATA_OVERWRITE = $(METADATA_OVERWRITE)
    RES_FORMAT_ATT_NEW = resources{}.format
    RES_FORMAT_ATT_REF = resources{}.format
    RES_NAME_ATT_NEW = resources{}.name
    RES_NAME_ATT_REF = resources{}.name_translated.en
    RES_URL_ATT_NEW = resources{}.url
    RES_URL_ATT_REF = resources{}.url
    TITLE_ATT_NEW = title
    TITLE_ATT_REF = title_translated.en
    Statistics -> StatisticsCalculator_Summary_2
    Update -> Junction_4
    Insert -> Junction_4
Note: Log statistics
StatisticsCalculator_Summary_2: Logger
    LOG_FEATURE = NONE
    MAXFEATS = 20
    MESSAGE:
      ************************
      **** None Geo Unchanged Report ****
      ************************

      @Value(_real_count) features were unchanged

      ************************
      ************************
      ************************
    SEVERITY = INFO
Junction_4
    -> AWS_TRANSLATE_2
JSON_PUBLISHER_NG
    FEATURE_TYPE = JSON_CONFIG_ON
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name_en
    Keywords_FR = tags{}.display_name_fr
    P-T_ABBR = $(P-T_ABBR)
    Subject_LIST = TBS_Subject{}.value
    Topic_LIST = TBS_Topic{}.value
    OUTPUT_LOCAL -> AttributeExposer_4
AttributeExposer_4
    ATTR_LIST = json_file,id
    -> AttributeCreator_6
AttributeCreator_6
    ATTR_TABLE = SET_TO text_line_data = @Value(json_file)
    -> text_line (writer TEXTLINE_1)
ATTRIBUTE_MAPPING_ERRORS_NON_GEO (writer XLSXW_1)
    attributes: error string(200), id string(200), _element_index string(200)

Bookmark: Generating TBS_SUBJECT list based on extracted topic
AttributeExposer_9
    ATTR_LIST = extracted_topic{}.value
    -> ListCopier_2
Note: Copy topic in a temp list
ListCopier_2
    DEST_LIST = TBS_Subject
    SRC_LIST = extracted_topic{}
    -> METADATA_VALUE_MAPPER_NG_9 [DATA_INPUT]
Note: Subject TBS
METADATA_VALUE_MAPPER_NG_9
    ATT_TO_MAP = TBS_Subject{}.value
    CODE_REFRESH = NO
    ENGLISH_REFRESH = YES
    ERROR_NOT_MAPPED = YES
    FEATURE_TYPE = Topic_Subject_ON
    FRENCH_REFRESH = NO
    IN_CSV_LOOKUP_TABLES_DIR = $(IN_CSV_LOOKUP_TABLES_DIR)
    P-T_ABBR = $(P-T_ABBR)
    -> AttributeExposer_14
AttributeExposer_14
    ATTR_LIST = TBS_Subject{}.value
    -> ListDuplicateRemover
Note: Removeing duplicates on subject value
ListDuplicateRemover
    SRC_LIST = TBS_Subject{}.value
    -> AttributeExposer_20

Bookmark: Generating Tbs Topic based on extracted topic
AttributeExposer_20
    ATTR_LIST = extracted_topic{}.value
    -> ListCopier_3
ListCopier_3
    DEST_LIST = TBS_Topic
    SRC_LIST = extracted_topic{}
    -> METADATA_VALUE_MAPPER_NG_10 [DATA_INPUT]
Note: Topic TBS
METADATA_VALUE_MAPPER_NG_10
    ATT_TO_MAP = TBS_Topic{}.value
    CODE_REFRESH = NO
    ENGLISH_REFRESH = YES
    ERROR_NOT_MAPPED = YES
    FEATURE_TYPE = Topic_Topic_ON
    FRENCH_REFRESH = NO
    IN_CSV_LOOKUP_TABLES_DIR = $(IN_CSV_LOOKUP_TABLES_DIR)
    P-T_ABBR = $(P-T_ABBR)
    -> AttributeExposer_15
AttributeExposer_15
    ATTR_LIST = TBS_Topic{}.value
    -> ListDuplicateRemover_2
ListDuplicateRemover_2
    SRC_LIST = TBS_Topic{}.value
    -> METADATA_VALUE_MAPPER_ERROR_MANAGER

Bookmark: Language translation
Note: Translate non geo features
AWS_TRANSLATE_2
    ACTIVATE_TRANSLATION = $(ACTIVATE_TRANSLATION)
    ATTR_2_TRANSLATE = notes,title
    ATTR_LIST_2_TRANSLATE = tags{}.display_name,resources{}.name
    MODE = English-->French
    -> JSON_PUBLISHER_NG
    TRANSLATION_PROBLEM -> TRANSLATION_PROBLEM_NONE_GEO (writer XLSXW_1)
TRANSLATION_PROBLEM_NONE_GEO (writer XLSXW_1)
    attributes: _aws_activation string(200), _mode string(200), _attr2translate string(200), _attrlist2translate string(200), _translation_status string(200)
