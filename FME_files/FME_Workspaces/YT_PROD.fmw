FME workspace YT_PROD.fmw
Title: YT_PROD
Description: Description 
This workbench read and trasform all the metadata for the Territory of Yukon (YT)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...). Extracted automatically using a Python script from the name of the FME Workspace (ex.: YT_PROD.fmw)
METADATA_OVERWRITE: Enable the overwite of the PyCSW.  Can take two values: Yes: Overwrite the content of the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: \ON\LOG\ON.log
OUT_JSON_LOCAL_DIR: Source directory to output JSON files. Defined as: \YT\JSON_LOCAL
OUT_XLS_NOTIFICATION: Source directory to output excel files. Defined as: \YT\XLS
OUT_XML_FAILED_DIR: Source directory to output failed XML files. Defined as: \YT\XML_FAILED
OUT_XML_LOCAL_DIR: Source directory to output Local Source XML files. Defined as: \YT\XML_LOCAL
OUT_XML_PASSED_DIR: Source directory to output passedXML files. Defined as: \YT\XML_PASSED
SAMPLE_SIZE: Number of features to process. Zero (0) means process all the features. A number n greater than 0 means sample or process only the first n features.
URL_VALIDATION : Indicates to validate or not created URL. (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = YES
- IN_OUT_WORKING_DIR = $(FME_SHAREDRESOURCE_DATA)\PT_Harvester
- SAMPLE_SIZE = 0
- URL_VALIDATION = Yes
- IN_CSV_LOOKUP_TABLES_DIR = $(IN_OUT_WORKING_DIR)\LOOKUP_TABLES
- IN_GMD_XML_TEMPLATE_DIR = $(IN_OUT_WORKING_DIR)\XML_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Data Directory

Writers:
- XLSXW_1: XLSXW to $(OUT_XLS_NOTIFICATION_DIR)
- TEXTLINE_1: TEXTLINE to $(OUT_XML_PASSED_DIR)
- TEXTLINE_2: TEXTLINE to $(OUT_XML_FAILED_DIR)
- TEXTLINE_3: TEXTLINE to $(OUT_XML_LOCAL_DIR)
- TEXTLINE_4: TEXTLINE to $(OUT_JSON_LOCAL_DIR)
- XLSXW_2: XLSXW to $(IN_OUT_WORKING_DIR)\YT\XLS
- XLSXW_3: XLSXW to $(IN_OUT_WORKING_DIR)\YT\XLS

Note: Est-ce qu'un Custom avec une liste de "Mapping Attributes" seriat souhaitable ?
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: lecture des données du portail et filtrage de licence
Creator
    GEOMTYPE = Geometry Object
    NUM = 1
    CREATED -> DateTimeStamper
DateTimeStamper
    DATETIME_ATTR = _toto
    STAMP_TYPE = date
    TIMEZONE = local
    -> VariableSetter
VariableSetter
    SCOPE = Global
    VALUE = @Value(_toto)
    VARNAME = _timestamp
    -> Tester_3
Tester_3
    BOOL_OP = OR
    COMPOSITE_TEST = 1
    TEST_CLAUSE = CASE_INSENSITIVE_TEST $(CATALOGUE_READER_SELECT) = Yes
    TEST_MODE = CASE_INSENSITIVE_TEST
    PASSED -> YT_CUSTOM_CATALOGUE_READER
    FAILED -> FeatureReader [INITIATOR]
YT_CUSTOM_CATALOGUE_READER
    DATA_OUTPUT -> ATTRIBUTE_VALUE_TEXT_CLEANER
Note: Reads pre-generated FFS file for testing as substitute for YT_CATALOGUE_READER
Note: I was able to find the missing records manually in YT portal. We can use a lookup toable to map name to ID and read correctly missing records
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER
Note: Removes whitespace from attributes
ATTRIBUTE_VALUE_TEXT_CLEANER
    -> TestFilter_3

Bookmark: Sampler
TestFilter_3
    DEFAULT_VALUE = SAMPLES FEATURES
    TEST_LIST = "BOOL_OP,OR,COMPOSITE_TEST,""""""1"""""",TEST_CLAUSE,TEST $(SAMPLE_SIZE) = 0",ALL FEATURES
    ALL FEATURES -> AttributeExposer_3
    SAMPLES FEATURES -> Sampler
Sampler
    RATE = $(SAMPLE_SIZE)
    SAMPLE_MODE = No
    SAMPLE_TYPE_LONG = First N Features
    SAMPLED -> AttributeExposer_3

Bookmark: Open License filtering
AttributeExposer_3
    ATTR_LIST = license_title
    -> Tester
Tester
    BOOL_OP = OR
    COMPOSITE_TEST = 1
    TEST_CLAUSE = TEST @Value(license_title) != ""
    TEST_MODE = TEST
    PASSED -> LICENSE_FILTER_NG
    FAILED -> VariableRetriever_15
LICENSE_FILTER_NG
    FEATURE_TYPE = License_YT
    IN_CSV_LOOKUP_TABLES_DIR = $(IN_CSV_LOOKUP_TABLES_DIR)
    LICENSE_ATT = @Value(license_title)
    P-T_ABBR = $(P-T_ABBR)
    LICENSE_FILTER_PASSED -> URL_HTTPS_MAKER [UUIDGenerator_Input]
    UNKNOWN_LICENSE -> VariableRetriever_14
VariableRetriever_14
    SCOPE = Global
    VALUE_ATTR = _timestamp
    VARNAME = _timestamp
    -> AttributeExposer_8
AttributeExposer_8
    ATTR_LIST = url
    -> unknown_license (writer XLSXW_1)
unknown_license (writer XLSXW_1)
    attributes: license_id string(200), license_title string(200), id string(200), _timestamp string(200), url string(200)
VariableRetriever_15
    SCOPE = Global
    VALUE_ATTR = _timestamp
    VARNAME = _timestamp
    -> AttributeExposer_9
AttributeExposer_9
    ATTR_LIST = url
    -> dataset_without licence (writer XLSXW_1)
dataset_without licence (writer XLSXW_1)
    attributes: license_title string(200), _timestamp string(200), url string(200)

Bookmark: Formatting dates, missing attributes and contacts
Note: Making HTTPS url to avoid issues
URL_HTTPS_MAKER
    URL_VALIDATION = $(URL_VALIDATION)
    -> AttributeExposer_11
AttributeExposer_11
    ATTR_LIST = url
    -> EMPTY_FORMAT_MAPPER_NG [DATA_INPUT]
EMPTY_FORMAT_MAPPER_NG
    CSV_FORMAT = format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> YT_DATE_FORMATTER
Note: Sets date values to iso yyyy-mm-dd format
YT_DATE_FORMATTER
    -> DEFAULT_ATTRIBUTE_MAPPER_NG
DEFAULT_ATTRIBUTE_MAPPER_NG
    FEATURE_TYPE = Default_YT
    IN_CSV_LOOKUP_TABLES_DIR = $(IN_CSV_LOOKUP_TABLES_DIR)
    P-T_ABBR = $(P-T_ABBR)
    -> YT_CONTACTS_MERGER
YT_CONTACTS_MERGER
    -> ATTRIBUTE_MANAGER_NG
ATTRIBUTE_MANAGER_NG
    IN_YAML_TEXT:
      notes:
          action: attribute_not_null
          attr2set: title

      iso_topic{}.topic_value:
          action: attribute_not_null
          attr2set: default_iso_topic

      east_bound_longitude:
          action: attribute_not_null
          attr2set: default_east_bound_longitude

      north_bound_latitude:
          action: attribute_not_null
          attr2set: default_north_bound_latitude

      south_bound_latitude:
          action: attribute_not_null
          attr2set: default_south_bound_latitude

      west_bound_longitude:
          action: attribute_not_null
          attr2set: default_west_bound_longitude

      progress_code:
          action: attribute_not_null
          attr2set: default_progress_code

      resource_update_cycle:
          action: attribute_not_null
          attr2set: default_resource_update_cycle

      spatialref_projection_name:
          action: attribute_not_null
          attr2set: default_spatialref_projection_name

      spatialref_projection_system:
          action: attribute_not_null
          attr2set: default_spatialref_projection_system

      spatialref_projection_system_version:
          action: attribute_not_null
          attr2set: default_spatialref_projection_system_version

      publisher:
          action: attribute_not_null
          attr2set: default_publisher

      tags{}.name:
          action: attribute_not_null
          attr2set: default_tags_display_name
    -> AttributeExposer_25
AttributeExposer_25
    ATTR_LIST = tags{}.name
    -> ListDuplicateRemover_2
Note: Removes duplicates from tags{} list attribute
ListDuplicateRemover_2
    SRC_LIST = tags{}.name
    -> RESOURCES_VALIDATOR
Note: Validates url, name and format on resources{} list items
RESOURCES_VALIDATOR
    -> RESOURCE_NAME_UNDERSCORE_REMOVER
Note: Removes all underscores from resources{}.name attributes. Long compounded names joined by underscores in this field can cause display formatting issues when published to the FGP.
RESOURCE_NAME_UNDERSCORE_REMOVER
    DATA_OUTPUT -> AttributeExposer_6

Bookmark: Adding weblink
AttributeExposer_6
    ATTR_LIST = url
    -> GEOPORTAL_WEBLINK_ADDER_NG
GEOPORTAL_WEBLINK_ADDER_NG
    FEATURE_TYPE = GeoportalWeblink_YT
    IN_CSV_LOOKUP_TABLES_DIR = $(IN_CSV_LOOKUP_TABLES_DIR)
    P-T_ABBR = $(P-T_ABBR)
    URL_VALIDATION = $(URL_VALIDATION)
    WEBLINK_WILDCARD = @Value(url)
    -> AttributeExposer_22

Bookmark: Ajusting and verifying contact{}.email
AttributeExposer_22
    ATTR_LIST = contacts{0}.email
    -> EMAIL_FORMAT_TESTER
EMAIL_FORMAT_TESTER
    DEFAULT_CONTACT_EMAIL = @Value(contacts{0}.email)
    -> METADATA_VALUE_MAPPER_NG_7 [DATA_INPUT]
Note: contacts{}.email
METADATA_VALUE_MAPPER_NG_7
    ATT_TO_MAP = contacts{}.email
    CODE_REFRESH = NO
    ENGLISH_REFRESH = YES
    ERROR_NOT_MAPPED = NO
    FEATURE_TYPE = Email
    FRENCH_REFRESH = NO
    IN_CSV_LOOKUP_TABLES_DIR = $(IN_CSV_LOOKUP_TABLES_DIR)
    P-T_ABBR = $(P-T_ABBR)
    -> GEO_NONE_GEO_SELECTOR

Bookmark: Geospatial/non-geospatial data filtering
Note: Recherche dans les formats
GEO_NONE_GEO_SELECTOR
    CSV_FILE_NAME = GeoSpatialValidation
    CSV_PATH = $(IN_CSV_LOOKUP_TABLES_DIR)
    CSV_PROVINCE = $(P-T_ABBR)
    YAML_DIRECTIVES:
      resources{}.format:
         domain: lookup_table_format
         spatial_type: overwrite
         not_found: log
         search_type: equals
    GEOSPATIAL -> Junction
    NONE_GEOSPATIAL -> GEO_NONE_GEO_SELECTOR_2
    LOG_ERROR -> GEOSPATIAL_FORMAT_NOT_MAPPED (writer XLSXW_1)
Note: Recherche dans les description
GEO_NONE_GEO_SELECTOR_2
    CSV_FILE_NAME = GeoSpatialValidation
    CSV_PATH = $(IN_CSV_LOOKUP_TABLES_DIR)
    CSV_PROVINCE = $(P-T_ABBR)
    YAML_DIRECTIVES:
      resources{}.description:
         domain: lookup_table_format
         spatial_type: overwrite
         not_found: no_log
         search_type: contains
    GEOSPATIAL -> Junction
    NONE_GEOSPATIAL -> GEO_NONE_GEO_SELECTOR_3
Note: Recherche dans les noms
GEO_NONE_GEO_SELECTOR_3
    CSV_FILE_NAME = GeoSpatialValidation
    CSV_PATH = $(IN_CSV_LOOKUP_TABLES_DIR)
    CSV_PROVINCE = $(P-T_ABBR)
    YAML_DIRECTIVES:
      resources{}.name:
         domain: lookup_table_format
         spatial_type: overwrite
         not_found: no_log
         search_type: contains
    GEOSPATIAL -> Junction
    NONE_GEOSPATIAL -> GEO_NONE_GEO_SELECTOR_4
Note: Recherche dans les noms pour valeur fixe
GEO_NONE_GEO_SELECTOR_4
    CSV_FILE_NAME = GeoSpatialValidation
    CSV_PATH = $(IN_CSV_LOOKUP_TABLES_DIR)
    CSV_PROVINCE = $(P-T_ABBR)
    YAML_DIRECTIVES:
      resources{}.name:
         domain: [ISO 19139 Geographic Information]
         spatial_type: no_overwrite
         not_found: no_log
         search_type: contains
    GEOSPATIAL -> Junction
    NONE_GEOSPATIAL -> MANUAL_GEOSPATIAL_SETTER_NG [DATA_INPUT]
Junction
    -> AttributeExposer_18
Note: Additional filtering step required for YT data. Items identified as NON-GEOSPATIAL in GEOSPATIAL_DATA_VALIDATOR were analyzed manually and a lookup table was created to identify non-filtered geo data and create the spatial_representation_type
MANUAL_GEOSPATIAL_SETTER_NG
    FEATURE_TYPE = UnmappedGeodata_YT
    IN_CSV_LOOKUP_TABLES_DIR = $(IN_CSV_LOOKUP_TABLES_DIR)
    P-T_ABBR = $(P-T_ABBR)
    GEOSPATIAL -> Tester_6
    NON-GEOSPATIAL -> Tester_2
    UNMAPPED_DATA -> VariableRetriever_13
VariableRetriever_13
    SCOPE = Global
    VALUE_ATTR = _timestamp
    VARNAME = _timestamp
    -> UNMAPPED_GEODATA_YT (writer XLSXW_1)
UNMAPPED_GEODATA_YT (writer XLSXW_1)
    attributes: id string(200), notes string(200), title string(200), url string(200), _timestamp string(200)
GEOSPATIAL_FORMAT_NOT_MAPPED (writer XLSXW_1)
    attributes: _geo_none_geo_status string(200), id string(200), _not_found_err_msg string(200), format string(200)
SPATIAL_TYPE_MAPPER_NG
    FEATURE_TYPE = UUID_Spatial_YT
    IN_CSV_LOOKUP_TABLES_DIR = $(IN_CSV_LOOKUP_TABLES_DIR)
    P-T_ABBR = $(P-T_ABBR)
    DATA_OUTPUT_FAILED -> VariableRetriever_12
    DATA_OUTPUT_PASSED -> Tester_6
VariableRetriever_12
    SCOPE = Global
    VALUE_ATTR = _timestamp
    VARNAME = _timestamp
    -> SPATIAL_TYPE_NOT_MAPPED (writer XLSXW_1)
SPATIAL_TYPE_NOT_MAPPED (writer XLSXW_1)
    attributes: _timestamp string(200)
Note: Select Geo
Tester_6
    BOOL_OP = OR
    COMPOSITE_TEST = 1
    TEST_CLAUSE = TEST $(ACTIVATE_GEO) = Yes
    TEST_MODE = TEST
    PASSED -> FORMAT_VALIDATOR
Note: Select Non-Geo
Tester_2
    BOOL_OP = OR
    COMPOSITE_TEST = 1
    TEST_CLAUSE = TEST $(ACTIVATE_NON_GEO) = Yes
    TEST_MODE = TEST
    PASSED -> METADATA_VALUE_MAPPER_NG_8 [DATA_INPUT]

Bookmark: Remettre en non géo les uuids fautifs. Des fois nos mots clés confondes le géo et le non géo
AttributeExposer_18
    ATTR_LIST = id
    -> FeatureMerger_2 [REQUESTOR]
Note: Reading UUID_2set_nongeo
LOOKUP_TABLES_READER_NG
    CSV_ENCODING = utf-8
    CSV_PATH = $(IN_CSV_LOOKUP_TABLES_DIR)
    FEATURE_TYPE = UUID_2set_nongeo
    PT = $(P-T_ABBR)
    -> AttributeExposer_13
AttributeExposer_13
    ATTR_LIST = id
    -> FeatureMerger_2 [SUPPLIER]
FeatureMerger_2
    ATTR_ACCUM_MODE = Merge Supplier
    ATTR_CONFLICT_RES = Use Requestor
    IGNORE_NULLS = No
    JOIN_KEYS = @Value(id) @Value(id) AUTO
    MERGE_TYPE = Attributes Only
    PROCESS_DUPS = NO
    REJECT_NULL_MISSING_KEYS = No
    SUPPLIERS_FIRST = No
    MERGED -> Tester_2
    UNMERGED_REQUESTOR -> SPATIAL_TYPE_MAPPER_NG [DATA_INPUT]

Bookmark: Attribute Validation
Note: Il y a deux versions (different date) du C-T (???)
Note: Verfication if URL is valid WMS call for WMS formats
FORMAT_VALIDATOR
    -> AttributeExposer_14
AttributeExposer_14
    ATTR_LIST = default_contact_email
    -> EMAIL_FORMAT_TESTER_2
EMAIL_FORMAT_TESTER_2
    DEFAULT_CONTACT_EMAIL = @Value(default_contact_email)
    -> METADATA_VALUE_MAPPER_NG [DATA_INPUT]

Bookmark: Attribute value mapper
Note: iso_topic{}.topic_value
METADATA_VALUE_MAPPER_NG
    ATT_TO_MAP = iso_topic{}.topic_value
    CODE_REFRESH = NO
    ENGLISH_REFRESH = YES
    ERROR_NOT_MAPPED = YES
    FEATURE_TYPE = Keyword
    FRENCH_REFRESH = NO
    IN_CSV_LOOKUP_TABLES_DIR = $(IN_CSV_LOOKUP_TABLES_DIR)
    P-T_ABBR = $(P-T_ABBR)
    -> METADATA_VALUE_MAPPER_NG_2 [DATA_INPUT]
Note: contacts{}.role
METADATA_VALUE_MAPPER_NG_2
    ATT_TO_MAP = contacts{}.role
    CODE_REFRESH = YES
    ENGLISH_REFRESH = YES
    ERROR_NOT_MAPPED = YES
    FEATURE_TYPE = role
    FRENCH_REFRESH = YES
    IN_CSV_LOOKUP_TABLES_DIR = $(IN_CSV_LOOKUP_TABLES_DIR)
    P-T_ABBR = $(P-T_ABBR)
    -> METADATA_VALUE_MAPPER_NG_3 [DATA_INPUT]
Note: spatial_representation_type
METADATA_VALUE_MAPPER_NG_3
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: progress_code
METADATA_VALUE_MAPPER_NG_4
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: spatailref_projection_name
METADATA_VALUE_MAPPER_NG_5
    ATT_TO_MAP = spatialref_projection_name
    CODE_REFRESH = NO
    ENGLISH_REFRESH = YES
    ERROR_NOT_MAPPED = YES
    FEATURE_TYPE = SpatialRef
    FRENCH_REFRESH = NO
    IN_CSV_LOOKUP_TABLES_DIR = $(IN_CSV_LOOKUP_TABLES_DIR)
    P-T_ABBR = $(P-T_ABBR)
    -> METADATA_VALUE_MAPPER_NG_6 [DATA_INPUT]
Note: resource_update_cycle
METADATA_VALUE_MAPPER_NG_6
    ATT_TO_MAP = resource_update_cycle
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_FORMAT_MAPPER_NG [DATA_INPUT]
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_VALUE_MAPPER_ERROR_MANAGER

Bookmark: Mapping error list creator
Note: Writes mapping errors to Excel file
METADATA_VALUE_MAPPER_ERROR_MANAGER
    ERROR_OUTPUT -> VariableRetriever_7
    DATA_OUTPUT -> AttributeExposer_15
VariableRetriever_7
    SCOPE = Global
    VALUE_ATTR = _timestamp
    VARNAME = _timestamp
    -> METADATA_MAPPING_ERRORS (writer XLSXW_1)
METADATA_MAPPING_ERRORS (writer XLSXW_1)
    attributes: error string(200), id string(200), _element_index string(200), _timestamp string(200)

Bookmark: Adjusting ESRI REST services
Note: Some ESRI REST services set by Yukon are not ESRI REST but web App. / Reset format ESRI REST to Web App to avoid issues with the RCS
AttributeExposer_15
    ATTR_LIST = resources{}
    -> ListElementCounter
ListElementCounter
    CNT_ATTR = _nb_res
    LIST_NAME = resources{}
    -> PythonCaller
PythonCaller
    PYTHONSOURCE:
      import fme
      import fmeobjects
      # Template Function interface:
      # When using this function, make sure its name is set as the value of
      # the 'Class or Function to Process Features' transformer parameter
      def processFeature(feature):
          for i in range(int(feature.getAttribute('_nb_res'))):
              if feature.getAttribute('resources{%i}.format'%(i))=='ESRI REST':
                  if r'https://yukon.maps.arcgis.com/apps' in feature.getAttribute('resources{%i}.url'%(i)):
                      feature.setAttribute('resources{%i}.format'%(i),'Web App')
    PYTHONSYMBOL = processFeature
    -> MORE_INFO_MANAGER

Bookmark: Data preparation for metadata section
Note: Tests the more_info{}.link list for valid attribute values and filters them out where missing
MORE_INFO_MANAGER
    -> REMOVE_BROKEN_URL_WMS_ESRI_REST

Bookmark: Data cleanup. Dropping broken web services
Note: Tests WMS/ESRI_REST resource URL's and removes them where broken
REMOVE_BROKEN_URL_WMS_ESRI_REST
    URL_VALIDATION = $(URL_VALIDATION)
    -> WMS_REST_LANGUAGE_FORMATTER
    FAULTY_URL_OUTPUT -> VariableRetriever_8
VariableRetriever_8
    SCOPE = Global
    VALUE_ATTR = _timestamp
    VARNAME = _timestamp
    -> MAP_SERVICE_URL_ERROR (writer XLSXW_1)
MAP_SERVICE_URL_ERROR (writer XLSXW_1)
    attributes: id string(200), url string(200), format string(200), _url_failure_message string(200), _timestamp string(200)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> GMD_SECTION_DATA_EXTRACTION

Bookmark: List and duplicate cleanup
Note: Creates lists and removes duplicates for GMD_Section
GMD_SECTION_DATA_EXTRACTION
    -> AttributeCreator_8

Bookmark: Creating geo/non-geo attribute
AttributeCreator_8
    ATTR_TABLE = SET_TO _typedatasets = geo
    -> AttributeCreator_3
AttributeCreator_18
    ATTR_TABLE = SET_TO _typedatasets = nongeo
    -> AttributeExposer

Bookmark: Configuring publishing info
AttributeCreator_3
    ATTR_TABLE = SET_TO csw_url = $(FORCED_PYCSW_URL)
    -> AttributeExposer_4
AttributeExposer_4
    ATTR_LIST = search_criteria_pycsw,csw_url
    -> METADATA_DELTA_FINDER_NG
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = csw_url
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> Logger
    Update -> Junction_3
    Insert -> Junction_3
    Delete -> DELETED_RECORDS (writer XLSXW_2)
Logger
    LOG_FEATURE = LOG_ONLY
    MAXCOORDS = 20
    MAXFEATS = 20
    MESSAGE:
      ************************
      **** Non Geo  Features: Unchanged Report ****
      ************************

      @Value(_real_count) features were unchanged

      ************************
      ************************
      ************************
    SEVERITY = INFO
Junction_3
    -> AttributeExposer
DELETED_RECORDS (writer XLSXW_2)
Note: Exposes PyCSW_Transaction attribute
AttributeExposer
    ATTR_LIST = PyCSW_Transaction
    -> AttributeFilter
Note: Filters items by PyCSW transaction type
AttributeFilter
    ATTR_NAME = PyCSW_Transaction
    ATTR_VALUES = <Empty>,<Missing>,<Null>,<Unfiltered>,No change,Update,Insert,Delete
    <EMPTY> -> Terminator
    <MISSING> -> Terminator
    <NULL> -> Terminator
    <UNFILTERED> -> Terminator
    No change -> AttributeExposer_16
    Update -> AttributeFilter_2
    Insert -> AttributeFilter_2
    Delete -> AttributeExposer_17
AttributeExposer_16
    ATTR_LIST = id
    -> Tester_5
Note: Selects items with no change for publishing, overwriting all existing data
Tester_5
    BOOL_OP = OR
    COMPOSITE_TEST = 1
    TEST_CLAUSE = TEST NO = YES
    TEST_MODE = TEST
    PASSED -> AttributeCreator
    FAILED -> StatisticsCalculator
StatisticsCalculator
    COMPUTE_HISTOGRAM = NO
    COUNT_ATTR = _count
    PREPEND_ATTR_NAME_CHOICE = For multiple results only
    STATS_ATTRS = id
    SUMMARY -> AttributeCreator_2
AttributeCreator_2
    ATTR_TABLE = SET_TO _real_count = @Evaluate(@Value(_count)-1)
    -> StatisticsCalculator_Summary
StatisticsCalculator_Summary: Logger
    LOG_FEATURE = NONE
    MAXFEATS = 20
    MESSAGE:
      ************************
      **** Unchanged Report ****
      ************************

      @Value(_real_count) features were unchanged

      ************************
      ************************
      ************************
    SEVERITY = INFO
Note: Reset to update
AttributeCreator
    ATTR_TABLE = SET_TO PyCSW_Transaction = Update
    -> AttributeFilter_2
Note: Geo/nongeo filtering
AttributeFilter_2
    ATTR_NAME = _typedatasets
    ATTR_VALUES = <Empty>,<Missing>,<Null>,<Unfiltered>,geo,nongeo
    <EMPTY> -> Terminator_3
    <MISSING> -> Terminator_3
    <NULL> -> Terminator_3
    <UNFILTERED> -> Terminator_3
    geo -> AWS_TRANSLATE
    nongeo -> AttributeExposer_24
Note: Feature needs to be geo or nongeo
Terminator_3
    MESSAGE = Translation Terminated - Feature needs to be part of goe or nongeo _typedatasets
Terminator
    MESSAGE = ERROR: Unknown _event value from Metadata_Delta
AttributeExposer_17
    ATTR_LIST = id
    -> AttributeKeeper
Note: Retains ID for list of deleted items
AttributeKeeper
    KEEP_ATTRS = id
    -> VariableRetriever_9
VariableRetriever_9
    SCOPE = Global
    VALUE_ATTR = _timestamp
    VARNAME = _timestamp
    -> DELETED_RECORDS (writer XLSXW_1)
DELETED_RECORDS (writer XLSXW_1)
    attributes: id string(200), _timestamp string(200)

Bookmark: Non-geo data processing
Note: resource_update_cycle
METADATA_VALUE_MAPPER_NG_8
    ATT_TO_MAP = resource_update_cycle
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> AttributeExposer_19
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_VALUE_MAPPER_ERROR_MANAGER_2
Note: Manage maping errors
METADATA_VALUE_MAPPER_ERROR_MANAGER_2
    ERROR_OUTPUT -> VariableRetriever_2
    DATA_OUTPUT -> ATTRIBUTE_MANAGER_NG_2
VariableRetriever_2
    SCOPE = Global
    VALUE_ATTR = _timestamp
    VARNAME = _timestamp
    -> NON_GEO_UNMAPPED_METADATA_VALUES (writer XLSXW_1)
Note: Writing errors into XLS spreadsheet
NON_GEO_UNMAPPED_METADATA_VALUES (writer XLSXW_1)
    attributes: error string(200), id string(200), _element_index string(200), _timestamp string(200)
Note: Ajustement des tags/topic/subject / Ajout de valeur par défault si vide
ATTRIBUTE_MANAGER_NG_2
    IN_YAML_TEXT:
      TBS_Subject{0}.value:
          action: attribute_not_null
          attr2set: default_tbs_subject

      TBS_Topic{0}.value:
          action: attribute_not_null
          attr2set: default_tbs_topic

      tags{0}.display_name:
          action: attribute_not_null
          attr2set: default_tbs_tag
    -> METADATA_DELTA_FINDER_NG_2
Note: Looking for differences in JSON files
METADATA_DELTA_FINDER_NG_2
    ABSTRACT_ATT_NEW = notes
    ABSTRACT_ATT_REF = notes_translated.en
    DATESTAMP_ATT_NEW = dat_last_modified
    DATESTAMP_ATT_REF = federal_date_modified
    ID_ATT_NEW = id
    ID_ATT_REF = id
    LOCAL_SOURCE = Yes
    LOCAL_SOURCE_DIR = $(OUT_JSON_LOCAL_DIR)
    LOCAL_SOURCE_FORMAT = XML
    METADATA_OVERWRITE = $(METADATA_OVERWRITE)
    RES_FORMAT_ATT_NEW = resources{}.format
    RES_FORMAT_ATT_REF = resources{}.format
    RES_NAME_ATT_NEW = resources{}.name
    RES_NAME_ATT_REF = resources{}.name_translated.en
    RES_URL_ATT_NEW = resources{}.url
    RES_URL_ATT_REF = resources{}.url
    TITLE_ATT_NEW = title
    TITLE_ATT_REF = title_translated.en
    Statistics -> Logger_2
    Update -> Junction_2
    Insert -> Junction_2
    Delete -> DELETED_RECORDS_NON_GEO (writer XLSXW_3)
Logger_2
    LOG_FEATURE = LOG_ONLY
    MAXCOORDS = 20
    MAXFEATS = 20
    MESSAGE:
      ************************
      ****  Geo  Features: Unchanged Report ****
      ************************

      @Value(_real_count) features were unchanged

      ************************
      ************************
      ************************
    SEVERITY = INFO
Junction_2
    -> AttributeExposer_21
Note: EXPOSE: PyCSW_Transaction
AttributeExposer_21
    ATTR_LIST = PyCSW_Transaction
    -> AttributeCreator_18
AttributeExposer_24
    ATTR_LIST = tags
    -> PythonCaller_5
PythonCaller_5
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass

          def input(self,feature):
              nom = feature.getAttribute('tags{}.name')
              position = []
              # Trouvons la longeur de chaque élément de la liste et vérifions si sa longeur est inférieure à 120 chars (on se donne du lousse p/r à la limite de 140 chars sachant que la traduction en français peut être plus longue).
              for elem in nom:
                  if len(elem) > 120:
                      position.append(elem)

              for elem2 in position:
                  nom.remove(elem2)

              feature.removeAttribute('tags{}.name')
              feature.setAttribute('tags{}.name', nom)

              self.pyoutput(feature)

          def close(self):
              pass
    PYTHONSYMBOL = FeatureProcessor
    -> AWS_TRANSLATE_2
Note: Translating english to french notes, title, keyword (tags) and resources.name
AWS_TRANSLATE_2
    ACTIVATE_TRANSLATION = $(ACTIVATE_TRANSLATION)
    ATTR_2_TRANSLATE = notes,title,sector
    ATTR_LIST_2_TRANSLATE = tags{}.display_name,resources{}.name
    MODE = English-->French
    -> JSON_PUBLISHER_NG
JSON_PUBLISHER_NG
    FEATURE_TYPE = YT_JSON_CONFIG
    IN_CSV_LOOKUP_TABLES_DIR = $(IN_CSV_LOOKUP_TABLES_DIR)
    JSON_RESOURCE_TEMPLATE = $(IN_TBS_JSON_TEMPLATE_DIR:)\TBS_RESOURCES_TEMPLATE.json
    JSON_ROOT_TEMPLATE = $(IN_TBS_JSON_TEMPLATE_DIR:)\TBS_ROOT_TEMPLATE.json
    Keywords_EN = tags{}.name
    Keywords_FR = tags{}.name_fr
    P-T_ABBR = $(P-T_ABBR)
    Subject_LIST = TBS_Subject{}.topic_value
    Topic_LIST = TBS_Topic{}.topic_value
    OUTPUT_LOCAL -> AttributeExposer_26
AttributeExposer_26
    ATTR_LIST = json_file,id
    -> AttributeCreator_7
AttributeCreator_7
    ATTR_TABLE = SET_TO text_line_data = @Value(json_file)
    -> text_line (writer TEXTLINE_4)
text_line (writer TEXTLINE_4)
    attributes: text_line_data buffer
DELETED_RECORDS_NON_GEO (writer XLSXW_3)

Bookmark: Generating TBS_SUBJECT list based iso_topic
AttributeExposer_19
    ATTR_LIST = iso_topic{}.topic_value
    -> ListCopier
Note: Copy tags in TBS_Subject list
ListCopier
    DEST_LIST = TBS_Subject
    SRC_LIST = iso_topic{}
    -> METADATA_VALUE_MAPPER_NG_9 [DATA_INPUT]
Note: TBS_Subject{}value
METADATA_VALUE_MAPPER_NG_9
    ATT_TO_MAP = TBS_Subject{}.topic_value
    CODE_REFRESH = NO
    ENGLISH_REFRESH = YES
    ERROR_NOT_MAPPED = YES
    FEATURE_TYPE = Subject_TBS_YT
    FRENCH_REFRESH = NO
    IN_CSV_LOOKUP_TABLES_DIR = $(IN_CSV_LOOKUP_TABLES_DIR)
    P-T_ABBR = $(P-T_ABBR)
    -> AttributeExposer_27
Note: exposing list attribute
AttributeExposer_27
    ATTR_LIST = TBS_Subject{}.topic_value
    -> ListDuplicateRemover
Note: Removeing duplicates on subject value
ListDuplicateRemover
    SRC_LIST = TBS_Subject{}.topic_value
    -> AttributeExposer_28

Bookmark: Generating TBS Topic based on presets.yaml
Note: exposing attribute
AttributeExposer_28
    ATTR_LIST = iso_topic{}
    -> ListCopier_2
Note: Copy tags in a temp list
ListCopier_2
    DEST_LIST = TBS_Topic
    SRC_LIST = iso_topic{}
    -> METADATA_VALUE_MAPPER_NG_10 [DATA_INPUT]
Note: TBS_Subject{}value
METADATA_VALUE_MAPPER_NG_10
    ATT_TO_MAP = TBS_Topic{}.topic_value
    CODE_REFRESH = NO
    ENGLISH_REFRESH = YES
    ERROR_NOT_MAPPED = YES
    FEATURE_TYPE = Topic_TBS_YT
    FRENCH_REFRESH = NO
    IN_CSV_LOOKUP_TABLES_DIR = $(IN_CSV_LOOKUP_TABLES_DIR)
    P-T_ABBR = $(P-T_ABBR)
    -> AttributeExposer_29
Note: exposing list attribute
AttributeExposer_29
    ATTR_LIST = TBS_Topic{}.topic_value
    -> PythonCaller_6
Note: Strip the default value in the lookup table named "No Topic"
PythonCaller_6
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass

          def input(self,feature):
              topic = feature.getAttribute('TBS_Topic{}.topic_value')

              topic = [i for i in topic if i != 'No Topic']
              #print(topic)

              feature.removeAttribute('TBS_Topic{}.topic_value')
              feature.setAttribute('TBS_Topic{}.topic_value', topic)

              self.pyoutput(feature)

          def close(self):
              pass
    PYTHONSYMBOL = FeatureProcessor
    -> METADATA_FORMAT_MAPPER_NG_2 [DATA_INPUT]

Bookmark: Language Translation
Note: Translates specific items from English to French
AWS_TRANSLATE
    ACTIVATE_TRANSLATION = $(ACTIVATE_TRANSLATION)
    ATTR_2_TRANSLATE = notes,title,sector
    ATTR_LIST_2_TRANSLATE = tags{}.display_name,resources{}.name
    MODE = English-->French
    -> XML_PUBLISHER_NG
    TRANSLATION_PROBLEM -> VariableRetriever_10
VariableRetriever_10
    SCOPE = Global
    VALUE_ATTR = _timestamp
    VARNAME = _timestamp
    -> TRANSLATION_PROBLEMS (writer XLSXW_1)
TRANSLATION_PROBLEMS (writer XLSXW_1)
    attributes: _aws_activation string(200), _mode string(200), _attr2translate string(200), _attrlist2translate string(200), _typedatasets string(200), PyCSW_Transaction string(200), id string(200), _translation_status string(200), _timestamp string(200)

Bookmark: XML CREATION AND WRITING
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER_NG
    FEATURE_TYPE = Config_YT
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    UPDATE_PASSED -> text_line (writer TEXTLINE_1)
    UPDATE_FAILED -> text_line (writer TEXTLINE_2)
