FME workspace PEI_PROD.fmw
Title: PEI_PROD
Description: Description 
This workbench read and trasform all the metadata for the province of Prince Edward Island (PEI)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC,PEI ...). Extracted automatically using a Python script from the name of the FME Workspace (ex.: PEI_PROD.fmw)
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: \PEI\LOG\PEI.log
OUT_JSON_LOCAL_DIR: Source directory to output JSON files. Defined as: \PEI\JSON_LOCAL
OUT_XLS_NOTIFICATION: Source directory to output excel files. Defined as: \PEI\XLS
OUT_XML_FAILED_DIR: Source directory to output failed XML files. Defined as: \PEI\XML_FAILED
OUT_XML_LOCAL_DIR: Source directory to output Local Source XML files. Defined as: \PEI\XML_LOCAL
OUT_XML_PASSED_DIR: Source directory to output passedXML files. Defined as: \PEI\XML_PASSED
SAMPLE_SIZE: Number of features to process. Zero (0) means process all the features. A number n greater than 0 means sample or process only the first n features.
URL_VALIDATION : Indicates to validate or not created URL. (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- P-T_ABBR = PEI
- METADATA_OVERWRITE = YES
- IN_OUT_WORKING_DIR = C:\Data\PT_Harvester
- URL_VALIDATION = No
- SAMPLE_SIZE = 0
- IN_CSV_LOOKUPTABLES_DIR = $(IN_OUT_WORKING_DIR)\LOOKUP_TABLES   # Lookup Tables Directory
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Resource Data

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_DIR)

unknown_date_extent (writer XLSXW_1)
    attributes: unmatched_date_extent string(200)
TestFilter
    DEFAULT_VALUE = <UNFILTERED>
    TEST_LIST = "BOOL_OP,OR,COMPOSITE_TEST,""""""1"""""",TEST_CLAUSE,TEST @LowerCase($(ACTIVATE_GEO)) = yes",GEO_ACTIVATE
    GEO_ACTIVATE -> Socrata_BoundingBoxExtractor [feature_input]
Socrata_BoundingBoxExtractor: SOCRATA_BOUNDING_BOX_EXTRACTOR
    DOMAIN = http://data.novascotia.ca
    SocrataAppToken = FL3Cxsebg0Vf6JQ0CnbMujHkQ
    URL_VALIDATION = $(URL_VALIDATION)
    feature_output -> METADATA_VALUE_MAPPER_NG [DATA_INPUT]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
invalid_metadata (writer XLSXW_1)
    attributes: id auto(20)
TestFilter_2
    DEFAULT_VALUE = <UNFILTERED>
    TEST_LIST = "BOOL_OP,OR,COMPOSITE_TEST,""""""1"""""",TEST_CLAUSE,TEST $(ACTIVATE_NON_GEO) = yes",NON-GEO_ACTIVATE,"BOOL_OP,OR,COMPOSITE_TEST,""""""1"""""",TEST_CLAUSE,TEST $(ACTIVATE_NON_GEO) = Yes",NON-GEO_ACTIVATE
    NON-GEO_ACTIVATE -> METADATA_VALUE_MAPPER_NG_6 [DATA_INPUT]
ATTRIBUTE_MAPPING_ERRORS_NON_GEO (writer XLSXW_1)
    attributes: error string(200), id string(200), _element_index string(200)
METADATA_DELTA_FINDER_NG
    ABSTRACT_ATT_NEW = description
    ABSTRACT_ATT_REF = notes_translated.en
    DATESTAMP_ATT_NEW = record_last_modified
    DATESTAMP_ATT_REF = federated_date_modified
    ID_ATT_NEW = id
    ID_ATT_REF = id
    LOCAL_SOURCE = Yes
    LOCAL_SOURCE_DIR = $(OUT_JSON_DIR)
    LOCAL_SOURCE_FORMAT = JSON
    METADATA_OVERWRITE = $(METADATA_OVERWRITE)
    RES_NAME_ATT_NEW = resources{}.name
    RES_NAME_ATT_REF = resources{}.name_translated.en
    RES_URL_ATT_NEW = resources{}.url
    RES_URL_ATT_REF = resources{}.url
    TITLE_ATT_NEW = title
    TITLE_ATT_REF = title_translated.en
    Statistics -> Logger
    Update -> Junction_3
    Insert -> Junction_3
    Delete -> DELETED_RECORDS_NON_GEO (writer XLSXW_1)
Logger
    LOG_FEATURE = LOG_ONLY
    MAXCOORDS = 20
    MAXFEATS = 20
    MESSAGE:
      ************************
      **** Non Geo  Features: Unchanged Report ****
      ************************

      @Value(_real_count) features were unchanged

      ************************
      ************************
      ************************
    SEVERITY = INFO
Junction_3
    -> AWS_TRANSLATE_3
AWS_TRANSLATE_3
    ACTIVATE_TRANSLATION = $(ACTIVATE_TRANSLATION)
    ATTR_2_TRANSLATE = notes,title,sector
    ATTR_LIST_2_TRANSLATE = tags{}.display_name,resources{}.name
    MODE = English-->French
    -> JSON_PUBLISHER_NG
    TRANSLATION_PROBLEM -> Translation_errors_non_geo (writer XLSXW_1)
JSON_PUBLISHER_NG
    FEATURE_TYPE = Config_JSON_PEI
    IN_CSV_LOOKUP_TABLES_DIR = $(IN_CSV_LOOKUPTABLES_DIR)
    JSON_RESOURCE_TEMPLATE = $(IN_TBS_JSON_TEMPLATE_DIR)/TBS_RESOURCES_TEMPLATE_NG.json
    JSON_ROOT_TEMPLATE = $(IN_TBS_JSON_TEMPLATE_DIR)/TBS_ROOT_TEMPLATE_NG.json
    Keywords_EN = tags{}.display_name
    Keywords_FR = tags{}.display_name_fr
    P-T_ABBR = $(P-T_ABBR)
    Subject_LIST = subject_tbs
    Topic_LIST = topic_tbs
    OUTPUT_LOCAL -> AttributeExposer_18
AttributeExposer_18
    ATTR_LIST = json_file,id
    -> AttributeCreator_8
AttributeCreator_8
    ATTR_TABLE = SET_TO text_line_data = @Value(json_file)
    -> text_line (writer TEXTLINE_4)
text_line (writer TEXTLINE_4)
    attributes: text_line_data buffer
Translation_errors_non_geo (writer XLSXW_1)
    attributes: id string(20), _timestamp string(20)
DELETED_RECORDS_NON_GEO (writer XLSXW_1)

Bookmark: lecture des données du portail socrata, filtrage de licence et fusion des métadonnées de vue externe
Creator_3
    GEOMTYPE = Geometry Object
    NUM = 1
    CREATED -> Tester_6
Tester_6
    BOOL_OP = OR
    COMPOSITE_TEST = 1
    TEST_CLAUSE = TEST $(CATALOGUE_READER_SELECT) = Yes
    TEST_MODE = TEST
    PASSED -> SOCRATA_READER_NG
    FAILED -> FeatureReader_2 [INITIATOR]
SOCRATA_READER_NG
    DOMAIN = https://data.princeedwardisland.ca
    -> ATTRIBUTE_VALUE_TEXT_CLEANER
FeatureReader_2
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> ATTRIBUTE_VALUE_TEXT_CLEANER
ATTRIBUTE_VALUE_TEXT_CLEANER
    -> TestFilter_3
AttributeExposer_3
    ATTR_LIST = id
    -> NullAttributeMapper
NullAttributeMapper
    ATTRCHOICE = Selected Attributes
    ATTRLIST = licenseId
    NEW_VALUE = none
    NULL_TREATMENT = New Value
    SOURCE_ATTR_VAL = Null Empty "Missing (Selected Attributes Only)"
    -> LICENSE_FILTER_NG
LICENSE_FILTER_NG
    FEATURE_TYPE = License_PEI
    IN_CSV_LOOKUP_TABLES_DIR = $(IN_CSV_LOOKUPTABLES_DIR)
    LICENSE_ATT = @Value(licenseId)
    P-T_ABBR = $(P-T_ABBR)
    LICENSE_FILTER_PASSED -> Socrata_MetadataMerger
    UNKNOWN_LICENSE -> unknown_licence (writer XLSXW_1)
Socrata_MetadataMerger: SOCRATA_METADATA_MERGER
    DOMAIN = https://data.princeedwardisland.ca
    -> DEFAULT_ATTRIBUTE_MAPPER_NG
    UnmergedAdvancedView -> unmergedAdvancedView (writer XLSXW_1)
unmergedAdvancedView (writer XLSXW_1)
    attributes: url string(200), format string(200), _seriesID string(200)
unknown_licence (writer XLSXW_1)
    attributes: license_id string(200), id string(200), title string(200)

Bookmark: Sampler
TestFilter_3
    DEFAULT_VALUE = SAMPLES FEATURES
    TEST_LIST = "BOOL_OP,OR,COMPOSITE_TEST,""""""1"""""",TEST_CLAUSE,TEST $(SAMPLE_SIZE) = 0",ALL FEATURES
    ALL FEATURES -> AttributeExposer_3
    SAMPLES FEATURES -> Sampler
Sampler
    RATE = $(SAMPLE_SIZE)
    SAMPLE_MODE = No
    SAMPLE_TYPE_LONG = First N Features
    SAMPLED -> AttributeExposer_3

Bookmark: Transformation vers modèle de travail et ajout des valeurs par défaults
DEFAULT_ATTRIBUTE_MAPPER_NG
    FEATURE_TYPE = Default_$(P-T_ABBR)
    IN_CSV_LOOKUP_TABLES_DIR = $(IN_CSV_LOOKUPTABLES_DIR)
    P-T_ABBR = $(P-T_ABBR)
    -> AttributeExposer_14

Bookmark: Date conversion
AttributeExposer_14
    ATTR_LIST = publicationDate,createdAt,viewLastModified
    -> DateTimeConverter
Note: Formats all date fields to ISO yyyy-mm-dd
DateTimeConverter
    DATETIME_ATTR = viewLastModified createdAt publicationDate
    IN_FORMAT = %s$
    OUT_FORMAT = %Y-%m-%d
    PASSTHROUGH = NO
    REPAIR_INPUT = YES
    TEST_INPUT = 1611946240
    -> ATTRIBUTE_MANAGER_NG
    <REJECTED> -> Error_Datetime (writer XLSXW_1)
Error_Datetime (writer XLSXW_1)
    attributes: publicationDate string(200), createdAt string(200), viewLastModified string(200), fme_rejection_code string(20)

Bookmark: Ajustement des attributes
Note: Default_Attributes
ATTRIBUTE_MANAGER_NG
    IN_YAML_TEXT:
      #Création des attributs par défault. Uniquement de attribute overwrite

      updated_frequency:
          action: attribute_overwrite
          attr2set: metadata.custom_fields.Dataset Information.Frequency of Issuance

      progress_code:
          action: attribute_overwrite
          attr2set: metadata.custom_fields.Dataset Information.Frequency of Issuance

      start_date_temp:
          action: attribute_overwrite
          attr2set: metadata.custom_fields.Dataset Information.Time Period Coverage Start Date

      end_date_temp:
          action: attribute_overwrite
          attr2set: metadata.custom_fields.Dataset Information.Time Period Coverage End Date

      resource.id:
          action: attribute_overwrite
          attr2set: id

      resource.type:
          action: attribute_overwrite
          attr2set: assetType

      tags_copy:
          action: attribute_overwrite
          attr2set: tags

      spatialref{0}.projection_name:
          action: attribute_overwrite
          attr2set: default_projection_name

      spatialref{0}.projection_system:
          action: attribute_overwrite
          attr2set: default_reference_system

      spatialref{0}.projection_system_version:
          action: attribute_overwrite
          attr2set: default_projection_system_version

      sector:
          action: attribute_overwrite
          attr2set: attribution

      notes:
          action: attribute_overwrite
          attr2set: description

      title:
          action: attribute_overwrite
          attr2set: name

      record_publish_date:
          action: attribute_overwrite
          attr2set: publicationDate

      record_last_modified:
          action: attribute_overwrite
          attr2set: viewLastModified

      record_create_date:
          action: attribute_overwrite
          attr2set: createdAt

      subject_tbs:
          action: attribute_overwrite
          attr2set: category

      topic_tbs:
          action: attribute_overwrite
          attr2set: category

      contact_email:
          action: attribute_overwrite
          attr2set: metadata.custom_fields.Dataset Information.Contact Email

      contact_role:
          action: attribute_overwrite
          attr2set: default_contact_role
    -> ATTRIBUTE_MANAGER_NG_3
Note: If null , phase 1
ATTRIBUTE_MANAGER_NG_3
    IN_YAML_TEXT:
      #Remplacement des attributs lorsque null
      tags_copy{0}:
          action: attribute_not_null
          attr2set: default_domain_tag

      # Default value for notes
      notes:
          action: attribute_not_null
          attr2set: name

      progress_code:
          action: attribute_not_null
          attr2set: default_progress_code

      start_date_temp:
          action: attribute_not_null
          attr2set: metadata.custom_fields.Dataset Information.Date Captured


      updated_frequency:
          action: attribute_not_null
          attr2set: default_updated_frequency

      contact_email:
           action: attribute_not_null
           attr2set: default_contact_email
    -> AttributeRemover_8

Bookmark: Replace Tags_copy{}
AttributeRemover_8
    LIST_ATTRS = tags{}
    -> PythonCaller_4
PythonCaller_4
    NEW_ATTRIBUTES = tags{}.display_name
    PYTHONSOURCE:
      import fme
      import fmeobjects
      # Template Function interface:
      # When using this function, make sure its name is set as the value of
      # the 'Class or Function to Process Features' transformer parameter
      def processFeature(feature):
          i=0
          for elem in feature.getAttribute('tags_copy{}'):
              feature.setAttribute('tags{%i}.display_name'%(i),elem)
              i+=1



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeRemover_9
AttributeRemover_9
    LIST_ATTRS = tags_copy{}
    -> AttributeExposer_7

Bookmark: Attribute Manager
AttributeExposer_7
    ATTR_LIST = start_date_temp,end_date_temp
    -> EXTRACT_COLLECTION_START_END_DATE
EXTRACT_COLLECTION_START_END_DATE
    CSV_PATH = $(IN_CSV_LOOKUPTABLES_DIR)
    DATE_EXTENT = @TrimRight(@Value(start_date_temp)/@Value(end_date_temp),/)
    FEATURE_TYPE = PEI_Manual_end_start_collection_date
    PT = $(P-T_ABBR)
    -> AttributeExposer_15
    Unworking_extent -> unknown_date_extent (writer XLSXW_1)
AttributeExposer_15
    ATTR_LIST = resource.id
    -> UNIQUE_ID_CREATOR_2
UNIQUE_ID_CREATOR_2
    UNIQUE_ATT = @Value(resource.id)
    -> GEOPORTAL_WEBLINK_ADDER_NG

Bookmark: Création de la liste des ressources pour les jeux de données
GEOPORTAL_WEBLINK_ADDER_NG
    FEATURE_TYPE = GeoportalWeblink_PEI
    IN_CSV_LOOKUP_TABLES_DIR = $(IN_CSV_LOOKUPTABLES_DIR)
    P-T_ABBR = $(P-T_ABBR)
    URL_VALIDATION = $(URL_VALIDATION)
    WEBLINK_WILDCARD = @Value(resource.id)
    -> SOCRATA_ADDITIONAL_ACCESS_POINTS_RESOURCES_EXTRACTOR
Note: Extraction des ressources dans additional access points / Crée la liste additional_access_points_resources
SOCRATA_ADDITIONAL_ACCESS_POINTS_RESOURCES_EXTRACTOR
    -> SOCRATA_ATTACHEMENTS_EXTRACTOR
Note: Extraction des resources dans les attachements / Crée la liste attachement_resources
SOCRATA_ATTACHEMENTS_EXTRACTOR
    SBN_URL_ROOT = https://data.princeedwardisland.ca
    URL_VALIDATION = $(URL_VALIDATION)
    -> SOCRATA_ADVANCED_VIEW_EXTRACTOR
Note: Extraction des ressources dans les vues avanacées / Crée la liste advancedview_resources
SOCRATA_ADVANCED_VIEW_EXTRACTOR
    -> SOCRATA_INSIDE_DB_EXTRACTOR_NG
SOCRATA_INSIDE_DB_EXTRACTOR_NG
    DOMAIN = https://data.princeedwardisland.ca
    Field_datatype = PEI_FieldType_NG
    Field_name = PEI_GeoDataFieldName
    IN_CSV_LOOKUP_TABLES_DIR = $(IN_CSV_LOOKUPTABLES_DIR)
    LinkBuilderNonGeo = PEI_LINKBUILDER_NONGEO
    P-T_ABBR = $(P-T_ABBR)
    URL_VALIDATION = $(URL_VALIDATION)
    linkbuilder_geo = PEI_LINKBUILDER_GEO
    -> AttributeExposer_13
    Unknown_field_datatype -> unknown_field_type (writer XLSXW_1)
ListElementCounter
    CNT_ATTR = _element_count
    LIST_NAME = resources{}
    -> Tester_2
Tester_2
    BOOL_OP = OR
    COMPOSITE_TEST = 1
    TEST_CLAUSE = TEST @Value(_element_count) > 1
    TEST_MODE = TEST
    PASSED -> EMPTY_FORMAT_MAPPER_NG [DATA_INPUT]
Note: Extraction du format
EMPTY_FORMAT_MAPPER_NG
    CSV_FORMAT = format
    CSV_MIME_TYPE = Mime_type
    IN_CSV_LOOKUP_TABLES_DIR = $(IN_CSV_LOOKUPTABLES_DIR)
    P-T_ABBR = $(P-T_ABBR)
    URL_VALIDATION = $(URL_VALIDATION)
    DATA_OUTPUT -> URL_HTTPS_MAKER [UUIDGenerator_Input]
URL_HTTPS_MAKER
    URL_VALIDATION = $(URL_VALIDATION)
    -> GEO_NONE_GEO_SELECTOR_2
unknown_field_type (writer XLSXW_1)
    attributes: fieldName string(200), dataTypeName string(200), columns string(200), _sub_uuid string(20), _element_index string(200)

Bookmark: Fusion des listes de resources dans une seule liste
AttributeExposer_13
    ATTR_LIST = resources{}.url
    -> ListCopier_2
ListCopier_2
    DEST_LIST = resources_copy
    SRC_LIST = resources{}
    -> AttributeRemover_5
AttributeRemover_5
    LIST_ATTRS = resources{}
    -> PythonCaller_5
PythonCaller_5
    NEW_ATTRIBUTES = resources{}.name resources{}.url resources{}.format resources{}.name_fr
    PYTHONSOURCE:
      import fme
      import fmeobjects
      logger = fmeobjects.FMELogFile()
      # Template Function interface:
      # When using this function, make sure its name is set as the value of
      # the 'Class or Function to Process Features' transformer parameter
      def processFeature(feature):
          list_list_name=[r'resources_copy',r'socrata_db_resources',r'advancedview_resources',r'additional_access_points_resources',r'attachement_resources']
          list_attr_name=[r'format',r'url',r'name',r'name_fr',r'spatial_type',r'fgp_publish']

          i=0





          for list_name in list_list_name:

              #Extracting number of resources
              list_url=feature.getAttribute('%s{}.url'%(list_name))
              if list_url:
                  #Looping in resources
                  for j in range(len(list_url)):
                      #Looping in attributes
                      for attr_name in list_attr_name:
                          feature.setAttribute('resources{%i}.%s'%(i,attr_name),feature.getAttribute('%s{%i}.%s'%(list_name,j,attr_name)))

                      #Changing index feature where new features
                      i=i+1
    PYTHONSYMBOL = processFeature
    -> ListDuplicateRemover_3
Note: Removing dupplicates on URL
ListDuplicateRemover_3
    SRC_LIST = resources{}.url
    -> AttributeExposer_16
AttributeExposer_16
    ATTR_LIST = resources_copy{},socrata_db_resources{},advancedview_resources{},additional_access_points_resources{},attachement_resources{}
    -> AttributeRemover_7
Note: Retrait des liste mergées
AttributeRemover_7
    LIST_ATTRS = additional_access_points_resources{} advancedview_resources{} attachement_resources{} resources_copy{} socrata_db_resources{}
    -> ListElementCounter

Bookmark: Filtrage geo / non-geo
Note: Sélection par format
GEO_NONE_GEO_SELECTOR_2
    CSV_FILE_NAME = GeoSpatialValidation
    CSV_PATH = $(IN_CSV_LOOKUPTABLES_DIR)
    CSV_PROVINCE = $(P-T_ABBR)
    YAML_DIRECTIVES:
      resources{}.format:
        domain: lookup_table_format
        spatial_type: overwrite
        not_found: log
        search_type: equals
    GEOSPATIAL -> AttributeExposer_4
    NONE_GEOSPATIAL -> GEO_NONE_GEO_SELECTOR_3
    LOG_ERROR -> unknown_format (writer XLSXW_1)
Note: Sélection par fgp publish (peut être défini sur les features memes si le format n'est pas nécessairement géo)
GEO_NONE_GEO_SELECTOR_3
    CSV_FILE_NAME = GeoSpatialValidation
    CSV_PATH = $(IN_CSV_LOOKUPTABLES_DIR)
    CSV_PROVINCE = $(P-T_ABBR)
    YAML_DIRECTIVES:
      resources{}.fgp_publish:
       domain: [oui]
       spatial_type: no_overwrite
       not_found: no_log
       search_type: equals
    GEOSPATIAL -> AttributeExposer_4
    NONE_GEOSPATIAL -> MANUAL_GEOSPATIAL_SETTER_NG [DATA_INPUT]
MANUAL_GEOSPATIAL_SETTER_NG
    FEATURE_TYPE = UnmappedGeoData_PEI
    IN_CSV_LOOKUP_TABLES_DIR = $(IN_CSV_LOOKUPTABLES_DIR)
    P-T_ABBR = $(P-T_ABBR)
    GEOSPATIAL -> Junction_2
    NON-GEOSPATIAL -> TestFilter_2
    UNMAPPED_DATA -> unknow_geo_non_geo (writer XLSXW_1)
unknow_geo_non_geo (writer XLSXW_1)
    attributes: id string(200), notes string(200), title string(200), url string(200)
unknown_format (writer XLSXW_1)
    attributes: format auto(20)

Bookmark: Adding spatial type manually
AttributeExposer_4
    ATTR_LIST = id,resource.id
    -> AttributeCreator_3
AttributeCreator_3
    ATTR_TABLE = SET_TO id_temp = @Value(id)
    -> AttributeCreator_4
AttributeCreator_4
    ATTR_TABLE = SET_TO id = @Value(resource.id)
    -> SPATIAL_TYPE_MAPPER_NG [DATA_INPUT]
SPATIAL_TYPE_MAPPER_NG
    FEATURE_TYPE = SpatialType_PEI
    IN_CSV_LOOKUP_TABLES_DIR = $(IN_CSV_LOOKUPTABLES_DIR)
    P-T_ABBR = $(P-T_ABBR)
    DATA_OUTPUT_FAILED -> Spatial_Type_Mapper_Failed (writer XLSXW_1)
    DATA_OUTPUT_PASSED -> AttributeExposer_8
Spatial_Type_Mapper_Failed (writer XLSXW_1)
    attributes: id string(20), title string(80), url string(80)
AttributeExposer_8
    ATTR_LIST = id_temp
    -> AttributeCreator_5
AttributeCreator_5
    ATTR_TABLE = SET_TO id = @Value(id_temp)
    -> AttributeRemover_2
AttributeRemover_2
    REMOVE_ATTRS = id_temp
    -> Junction_2
Junction_2
    -> TestFilter

Bookmark: Metadata Value Mapping
Note: Topic
METADATA_VALUE_MAPPER_NG
    ATT_TO_MAP = category
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_2 [DATA_INPUT]
Note: Role
METADATA_VALUE_MAPPER_NG_2
    ATT_TO_MAP = contact_role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_3 [DATA_INPUT]
Note: updated_frequency
METADATA_VALUE_MAPPER_NG_3
    ATT_TO_MAP = updated_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: progress_code
METADATA_VALUE_MAPPER_NG_4
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: spatial_representation_type
METADATA_VALUE_MAPPER_NG_5
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: resources{}.format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_ERROR_MANAGER
METADATA_VALUE_MAPPER_ERROR_MANAGER
    ERROR_OUTPUT -> ATTRIBUTE_MAPPING_ERRORS (writer XLSXW_1)
    DATA_OUTPUT -> AttributeExposer_9
AttributeExposer_9
    ATTR_LIST = mapping_errors{}
    -> AttributeRemover_6
Note: Removing error list
AttributeRemover_6
    LIST_ATTRS = mapping_errors{}
    -> RESOURCE_NAME_UNDERSCORE_REMOVER
ATTRIBUTE_MAPPING_ERRORS (writer XLSXW_1)
    attributes: error string(200), id string(200), _element_index string(200)

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    URL_VALIDATION = $(URL_VALIDATION)
    -> WMS_REST_LANGUAGE_FORMATTER
    FAULTY_URL_OUTPUT -> MAP_SERVICE_URL_ERRORMAP (writer XLSXW_1)
MAP_SERVICE_URL_ERRORMAP (writer XLSXW_1)
    attributes: id string(200), url string(200), format string(200), _url_failure_message string(200)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> AttributeCreator_11

Bookmark: New Bookmark
AttributeCreator_11
    ATTR_TABLE = SET_TO csw_url = $(FORCED_PYCSW_URL)
    -> AttributeExposer_2
AttributeExposer_2
    ATTR_LIST = search_criteria_pycsw
    -> METADATA_DELTA_FINDER_NG_3
METADATA_DELTA_FINDER_NG_3
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> Logger_2
    Update -> Junction
    Insert -> Junction
    Delete -> DELETED_RECORDS_GEO (writer XLSXW_1)
Logger_2
    LOG_FEATURE = LOG_ONLY
    MAXCOORDS = 20
    MAXFEATS = 20
    MESSAGE:
      ************************
      ****  Geo  Features: Unchanged Report ****
      ************************

      @Value(_real_count) features were unchanged

      ************************
      ************************
      ************************
    SEVERITY = INFO
Junction
    -> AWS_TRANSLATE_2
DELETED_RECORDS_GEO (writer XLSXW_1)

Bookmark: AWS Translation
Note: English to french / notes, / title, / tags_en / resources name
AWS_TRANSLATE_2
    ACTIVATE_TRANSLATION = $(ACTIVATE_TRANSLATION)
    ATTR_2_TRANSLATE = notes,title,sector
    ATTR_LIST_2_TRANSLATE = tags{}.display_name,resources{}.name
    MODE = English-->French
    -> XML_PUBLISHER_NG
    TRANSLATION_PROBLEM -> Translation_errors_geo (writer XLSXW_1)
Translation_errors_geo (writer XLSXW_1)
    attributes: id string(20), _timestamp string(20)

Bookmark: XML CREATION AND WRITING
XML_PUBLISHER_NG
    FEATURE_TYPE = Config_PEI
    IN_CSV_LOOKUP_TABLES_DIR = $(IN_CSV_LOOKUPTABLES_DIR)
    LOCAL_WRITER = $(LOCAL_WRITER)
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> text_line (writer TEXTLINE_2)
    UPDATE_FAILED -> invalid_metadata (writer XLSXW_1)

Bookmark: Mapping des valeurs vers le modèle de TBS
Note: updated_frequency
METADATA_VALUE_MAPPER_NG_6
    ATT_TO_MAP = updated_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUPTABLES_DIR)
    P-T_ABBR = $(P-T_ABBR)
    -> METADATA_FORMAT_MAPPER_NG_2 [DATA_INPUT]
Note: resources{}.format
METADATA_FORMAT_MAPPER_NG_2
    ATT_TO_MAP = resources{}.format
    ERROR_NOT_MAPPED = YES
    FEATURE_TYPE = Format_TBS
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    -> METADATA_VALUE_MAPPER_NG_7 [DATA_INPUT]
Note: subject_tbs
METADATA_VALUE_MAPPER_NG_7
    ATT_TO_MAP = subject_tbs
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUPTABLES_DIR)
    P-T_ABBR = $(P-T_ABBR)
    -> METADATA_VALUE_MAPPER_NG_8 [DATA_INPUT]
Note: subject_tbs
METADATA_VALUE_MAPPER_NG_8
    ATT_TO_MAP = topic_tbs
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUPTABLES_DIR)
    P-T_ABBR = $(P-T_ABBR)
    -> METADATA_VALUE_MAPPER_ERROR_MANAGER_2
METADATA_VALUE_MAPPER_ERROR_MANAGER_2
    ERROR_OUTPUT -> ATTRIBUTE_MAPPING_ERRORS_NON_GEO (writer XLSXW_1)
    DATA_OUTPUT -> METADATA_DELTA_FINDER_NG

FME custom transformer NS_ATTRIBUTE_MANAGER

Input (input)
    -> AttributeExposer_3
AttributeExposer_3
    ATTR_LIST = id,assetType,tags{},default_domain_tag,default_projection_name,default_projection_system_version,default_reference_system,attribution,description,name,publicationDate,viewLastModified,createdAt
    -> AttributeCreator_5
AttributeCreator_5
    ATTR_TABLE:
      SET_TO resource.id = @Value(id)
      SET_TO resource.type = @Value(assetType)
    -> UNIQUE_ID_CREATOR
UNIQUE_ID_CREATOR
    UNIQUE_ATT = @Value(resource.id)
    -> Tester_4
Tester
    BOOL_OP = OR
    COMPOSITE_TEST = 1
    TEST_CLAUSE = TEST @Value(description) != ""
    TEST_MODE = TEST
    PASSED -> AttributeCreator_8
    FAILED -> AttributeCreator
AttributeCreator
    ATTR_TABLE = SET_TO description = @Value(name)
    -> AttributeCreator_8
Note: Setting default projection system
AttributeCreator_8
    ATTR_TABLE:
      SET_TO spatialref{0}.projection_name = @Value(default_projection_name)
      SET_TO spatialref{0}.projection_system = @Value(default_reference_system)
      SET_TO spatialref{0}.projection_system_version = @Value(default_projection_system_version)
    -> AttributeCreator_9
Note: Creating inhouse model attribute base on NS format
AttributeCreator_9
    ATTR_TABLE:
      SET_TO sector = @Value(attribution)
      SET_TO notes = @Value(description)
      SET_TO title = @Value(name)
      SET_TO record_publish_date = @Value(publicationDate)
      SET_TO record_last_modified = @Value(viewLastModified)
      SET_TO record_create_date = @Value(createdAt)
    -> Output (output)

Bookmark: Managing tags
Tester_4
    BOOL_OP = OR
    COMPOSITE_TEST = 1
    TEST_CLAUSE = TEST tags{0} ATTRIBUTE_HAS_A_VALUE ""
    TEST_MODE = TEST
    PASSED -> ListCopier
    FAILED -> AttributeCreator_2
AttributeCreator_2
    ATTR_TABLE = SET_TO tags{0} = @Value(default_domain_tag)
    -> ListCopier
ListCopier
    DEST_LIST = tags_copy
    SRC_LIST = tags{}
    -> AttributeRemover
AttributeRemover
    LIST_ATTRS = tags{}
    -> PythonCaller
PythonCaller
    NEW_ATTRIBUTES = tags{}.display_name
    PYTHONSOURCE:
      import fme
      import fmeobjects
      # Template Function interface:
      # When using this function, make sure its name is set as the value of
      # the 'Class or Function to Process Features' transformer parameter
      def processFeature(feature):
          i=0
          for elem in feature.getAttribute('tags_copy{}'):
              feature.setAttribute('tags{%i}.display_name'%(i),elem)
              i+=1



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeRemover_2
AttributeRemover_2
    LIST_ATTRS = tags_copy{}
    -> Tester

Bookmark: DateTime Conversion
Note: Formats all date fields to ISO yyyy-mm-dd
DateTimeConverter [off]
    DATETIME_ATTR = record_create_date record_last_modified record_publish_date
    IN_FORMAT = %s$
    OUT_FORMAT = %Y-%m-%d
    PASSTHROUGH = NO
    REPAIR_INPUT = YES
    TEST_INPUT = 1611946240
    -> Output (output) [off]
    <REJECTED> -> error_datetime_output (output) [off]
Output (output)
error_datetime_output (output)

FME custom transformer ListSlicer_2
Replaces an existing list with a list containing elements of the slicing range which is determined by the starting index and the number of elements.
If the source list was a structured one like "_list{}.foo", "_list{}.bar", all the members belonging to the same base name will be replaced.
Example
When the source list contains:
_list{0}.foo = '0'
_list{1}.foo = '1'
_list{2}.foo = '2'
_list{3}.foo = '3'
_list{4}.foo = '4'
_list{0}.bar = 'A'
_list{1}.bar = 'B'
_list{2}.bar = 'C'
_list{3}.bar = 'D'
_list{4}.bar = 'E'
After slicing with Starting Element Index = 1 and Number of Elements to Slice = 3, the list will be replaced with:
_list{0}.foo = '1'
_list{1}.foo = '2'
_list{2}.foo = '3'
_list{0}.bar = 'B'
_list{1}.bar = 'C'
_list{2}.bar = 'D'
Note: This transformer contains a Python script which was tested with both Python 2.7 interpreter and Python 3.6 interpreter.
Parameters
    Source List Attribute:
Select a source list attribute to be sliced.
    Starting Element Index:
Specify index of the element to start slicing. The index is always 0-based.
If specified index is less than 0, this transformer considers the starting index as 0.
    Number of Elements to Slice:
Specify the number of elements to be sliced.
If specified number is equal to 0, this transformer removes every element from the source list (i.e. removes the source list).
If specified number is less than 0, this transformer considers the number as 0.
    Null Elements Treatment:
Select how treat <null> elements in the slicing range.
"Replace with Empty String" - Every <null> element will be replaced with an empty string.
"Replace with New Value" - Every <null> element will be replaced with a value specified as New Value for Null parameter.
"Replace with Missing" - Every <null> element will be removed. The element will be missing in the resultant list.
"Leave Null" - Every <null> element will be left in the resultant list as <null>.
    New Value for Null:
Specify a value to be used for replacing <null> elements.
This parameter is used only if you selected "Replace with New Value" to Null Elements Treatment. Otherwise, it'll be just ignored.
    Missing Elements Treatment:
Select how treat <missing> elements in the slicing range.
"Replace with Empty String" - Every <missing> element will be replaced with an empty string.
"Replace with New Value" - Every <missing> element will be replaced with a value specified as New Value for Missing parameter.
"Replace with Null" - Every <missing> element will be replaced with <null>.
"Leave Missing" - Every <missing> element will be still missing in the resultant list.
    New Value for Missing:
Specify a value to be used for replacing <missing> elements.
This parameter is used only if you selected "Replace with New Value" to Missing Elements Treatment. Otherwise, it'll be just ignored.

Parameters:
- SRC_LIST =   # " " Source List Attribute
- START_INDEX = 0   # Starting Element Index
- NUM_ELEMENTS =   # Number of Elements to Slice
- NULL_TREATMENT = empty
- NEWVALUE_FOR_NULL =   # New Value for Null
- MISSING_TREATMENT = empty
- NEWVALUE_FOR_MISSING =   # New Value for Missing

Input (input)
    -> ParameterFetcher
ParameterFetcher
    ATTR_LIST = __listslicer.src_list {$(SRC_LIST)} __listslicer.start_index {$(START_INDEX)} __listslicer.num_elements {$(NUM_ELEMENTS)} __listslicer.null_treat {$(NULL_TREATMENT)} __listslicer.newvalue_for_null {$(NEWVALUE_FOR_NULL)} __listslicer.missing_treat {$(MISSING_TREATMENT)} __listslicer.newvalue_for_missing {$(NEWVALUE_FOR_MISSING)}
    -> PythonCaller
PythonCaller
    HIDE_ATTRIBUTES = __listslicer.src_list __listslicer.start_index __listslicer.num_elements __listslicer.null_treat __listslicer.newvalue_for_null __listslicer.missing_treat __listslicer.newvalue_for_missing
    PYTHONSOURCE:
      # 2014-07-27, Takashi Iijima, Original Implementation
      # 2014-08-02, Takashi Iijima, Resolved encoding issue on list name
      # 2018-06-14, Takashi Iijima, Updated to support both Python 2.7 and Python 3.x
      # 2020-04-30, Takashi Iijima, Changed default Python interpreter version to 3.x, saved with FME 2017.1.2.1

      import fmeobjects, re

      class ListSlicer(object):
          def __init__(self):
              import platform
              if platform.python_version_tuple()[0] == '2':
                  import locale
                  loc = locale.getdefaultlocale()
                  enc = loc[1] if loc else 'utf_8'
                  self.toStr = lambda s: s.encode(enc) if isinstance(s, unicode) else s
              else:
                  self.toStr = lambda s: s

          def input(self, feature):
              listName = self.toStr(feature.getAttribute('__listslicer.src_list'))
              prefix = listName[:-2]
              regexListElement = re.compile(r'^%s\{(\d+)\}(.*)$' % prefix)

              # Find maximum element index and collect suffixes of target list members.
              maxIndex = -1
              suffixes = set([])
              for name in [self.toStr(s) for s in feature.getAllAttributeNames()]:
                  m = regexListElement.match(name)
                  if m:
                      if maxIndex < int(m.group(1)):
                          maxIndex = int(m.group(1))
                      suffixes.add(self.toStr(m.group(2)))

              startIndex = int(feature.getAttribute('__listslicer.start_index'))
              if startIndex < 0:
                  startIndex = 0
              numElements = int(feature.getAttribute('__listslicer.num_elements'))
              if numElements < 0:
                  numElements = 0

              nullTreat = feature.getAttribute('__listslicer.null_treat')
              newValueToNull = feature.getAttribute('__listslicer.newvalue_for_null')

              missingTreat = feature.getAttribute('__listslicer.missing_treat')
              newValueToMissing = feature.getAttribute('__listslicer.newvalue_for_missing')

              for suffix in suffixes:
                  # Move elements from slicing range to head of the list.
                  for i in range(numElements):
                      srcName = '%s{%d}%s' % (prefix, startIndex + i, suffix)
                      destName = '%s{%d}%s' % (prefix, i, suffix)

                      isNull, isMissing, type = feature.getAttributeNullMissingAndType(srcName)
                      if isNull:
                          if nullTreat == 'empty':
                              feature.setAttribute(destName, '')
                          elif nullTreat == 'newvalue':
                              feature.setAttribute(destName, newValueToNull)
                          elif nullTreat == 'missing':
                              feature.removeAttribute(destName)
                          elif nullTreat == 'as_is':
                              feature.setAttributeNullWithType(destName, type)
                          else:
                              raise fmeobjects.FMEException('Debug error: Null Treatment')

                      elif isMissing:
                          if missingTreat == 'empty':
                              feature.setAttribute(destName, '')
                          elif missingTreat == 'newvalue':
                              feature.setAttribute(destName, newValueToMissing)
                          elif missingTreat == 'null':
                              feature.setAttributeNullWithType(destName, type)
                          elif missingTreat == 'as_is':
                              feature.removeAttribute(destName)
                          else:
                              raise fmeobjects.FMEException('Debug error: Missing Treatment')

                      else:
                          feature.setAttribute(destName, feature.getAttribute(srcName))

                  # Remove excess elements.
                  for i in range(numElements, maxIndex + 1):
                      feature.removeAttribute('%s{%d}%s' % (prefix, i, suffix))

              feature.removeAttrsWithPrefix('__listslicer.')
              self.pyoutput(feature)

          def close(self):
              pass
    PYTHONSYMBOL = ListSlicer
    -> Output (output)
Output (output)

FME custom transformer CreatingHashKeyFromAttributes_2
Description 
This custom transformer is using a hashing function in order to create a unique identifier (value) for a metadata records.  Strategic fields (attributes) from the metadata records are used in the hashing function in order to create a very representative unique value for each metadata records.
Input Ports 
Input: The input metadata records to process.
Output Ports 
OUTPUT: The output metdata records with an attribute representing a unique hash value for the metadata record (_global_hashkey)
Parameters 
ID_ATT: Name of the attribute containing the identification of the metadata record
DATESTAMP_ATT: Name of the attribute containing the date stamp of the metadata record 
RES_URL_ATT: Name of the attribute containing the resource URL of the metadata record
RES_NAME_ATT: Name of the attribute containing the resource name of the metadata record
TITLE_ATT: Name of the attribute containing the title of the metadata record
ABSTRACT_ATT: Name of the attribute containing the description of the abstract of the metadata record
RES_FORMAT_ATT: Name of the attribute containing the format of the resource of the metadatarecord

Parameters:
- ID_ATT =
- DateStamp_ATT =
- Resources_URL_ATT =
- Resources_Name_ATT =
- Title_ATT =
- Abstract_ATT =
- Resources_Format_ATT =

Cloner_Input (input)
    -> AttributeCreator_4
AttributeKeeper_Output (output)

Bookmark: Creating hasing key to evaluate value
AttributeCreator_4
    ATTR_TABLE:
      SET_TO ID_ATT = $(ID_ATT)
      SET_TO TITLE_ATT = $(Title_ATT)
      SET_TO ABSTRACT_ATT = $(Abstract_ATT)
      SET_TO DATESTAMP_ATT = $(DateStamp_ATT)
      SET_TO RESOURCES_NAME_ATT = $(Resources_Name_ATT)
      SET_TO RESOURCES_URL_ATT = $(Resources_URL_ATT)
      SET_TO RESOURCES_FORMAT_ATT = $(Resources_Format_ATT)
    -> PythonCaller_2
Note: Creating hash key
PythonCaller_2
    PYTHONSOURCE:
      import fme
      import fmeobjects
      import hashlib
      # Template Function interface:
      # When using this function, make sure its name is set as the value of
      # the 'Class or Function to Process Features' transformer parameter

      class FeatureProcessor(object):
          def __init__(self):
              pass
          def input(self,feature):
              # Create the hash value for the ID
              id=feature.getAttribute(feature.getAttribute('ID_ATT')).replace('\t',' ').lstrip(' ').rstrip(' ')
              id_haskey=hashlib.sha256(id.encode('utf-8')).hexdigest()
      #        feature.setAttribute('_hash_id',id_haskey)

              # Create the hash value for the Date stamp
              datestamp=feature.getAttribute(feature.getAttribute('DATESTAMP_ATT')).replace('\t',' ').lstrip(' ').rstrip(' ')
              datestamp_haskey=hashlib.sha256(datestamp.encode('utf-8')).hexdigest()
      #        feature.setAttribute('_hash_datestamp',datestamp_haskey)

              # Create the hash value for the Abstract
              abstract=feature.getAttribute(feature.getAttribute('ABSTRACT_ATT')).replace('\n', ' ').replace('\r', '').replace('\t',' ').lstrip(' ').rstrip(' ')
              abstract_haskey=hashlib.sha256(abstract.encode('utf-8')).hexdigest()
      #        feature.setAttribute('_hash_abstract',abstract_haskey)

              # Create the hash value for the Title
              title=feature.getAttribute(feature.getAttribute('TITLE_ATT')).replace('\n', ' ').replace('\r', '').replace('\t',' ').lstrip(' ').rstrip(' ')
              title_haskey=hashlib.sha256(title.encode('utf-8')).hexdigest()
      #        feature.setAttribute('_hash_title',title_haskey)

              ## Create the hash value for the esources URL
              res_url=feature.getAttribute(feature.getAttribute('RESOURCES_URL_ATT'))
              url_hash=[]
              if res_url:
                  # Loop over each resources URL if it is a list
                  for url in res_url:
                      url_hash.append(hashlib.sha256(url.lstrip(' ').rstrip(' ').encode('utf-8')).hexdigest())

                  if len(url_hash)>1:
                      url_hash.sort()
                      url_hash=hashlib.sha256(''.join(url_hash).encode('utf-8')).hexdigest()
                  else:
                      url_hash=''.join(url_hash)
              else:
                  # It's not a list
                  res_url=feature.getAttribute(feature.getAttribute('RESOURCES_URL_ATT').replace('{}',''))
                  url_hash=hashlib.sha256(res_url.encode('utf-8')).hexdigest()
      #        feature.setAttribute('_hash_url',url_hash)

              # Create the hash value for the Resource_name
              res_name=feature.getAttribute(feature.getAttribute('RESOURCES_NAME_ATT'))
              name_hash=[]
              if res_name:
                  # Loop over each resources name if it is a list
                  for name in res_name:
                      name_hash.append(hashlib.sha256(name.replace('\t',' ').lstrip(' ').rstrip(' ').encode('utf-8')).hexdigest())

                  if len(name_hash)>1:
                      name_hash.sort()
                      name_hash=hashlib.sha256(''.join(name_hash).encode('utf-8')).hexdigest()
                  else:
                      name_hash=''.join(name_hash)
              else:
                  # It is not a list
                  res_name=feature.getAttribute(feature.getAttribute('RESOURCES_NAME_ATT').replace('{}',''))
                  name_hash=hashlib.sha256(res_name.encode('utf-8')).hexdigest()
      #        feature.setAttribute('_hash_name',name_hash)

              # Create the hash value for the Resource_format
              if feature.getAttribute('RESOURCES_FORMAT_ATT'):
                  res_format=feature.getAttribute(feature.getAttribute('RESOURCES_FORMAT_ATT'))
                  format_hash=[]
                  if res_format:
                      for format in res_format:
                          format_hash.append(hashlib.sha256(format.replace('\t',' ').lstrip(' ').rstrip(' ').encode('utf-8')).hexdigest())

                      if len(format_hash)>1:
                          format_hash.sort()
                          format_hash=hashlib.sha256(''.join(format_hash).encode('utf-8')).hexdigest()
                      else:
                          format_hash=''.join(format_hash)

                  else:
                      res_format=feature.getAttribute(feature.getAttribute('RESOURCES_FORMAT_ATT').replace('{}',''))
                      format_hash=hashlib.sha256(res_format.encode('utf-8')).hexdigest()

      #            feature.setAttribute('_hash_format',format_hash)
              else:
                  format_hash='not_validated'
      #            feature.setAttribute('_hash_format',format_hash)

              # Create the glabal hash value by using all the intermediate hash values
              global_string='%s%s%s%s%s%s%s'%(id_haskey,datestamp_haskey,abstract_haskey,title_haskey,url_hash,name_hash,format_hash)
              hashkey=hashlib.sha256(global_string.encode('utf-8'))
              feature.setAttribute('_global_hashkey',hashkey.hexdigest())

              self.pyoutput(feature)
          def close(self):
              pass
    PYTHONSYMBOL = FeatureProcessor
    -> AttributeRemover
AttributeRemover
    REMOVE_ATTRS = RESOURCES_NAME_ATT,RESOURCES_URL_ATT,ID_ATT,DATESTAMP_ATT,ABSTRACT_ATT,TITLE_ATT
    -> AttributeKeeper_Output (output)

FME custom transformer SOCRATA_INSIDE_DB_EXTRACTOR_NG

Parameters:
- DOMAIN =
- URL_VALIDATION = Yes
- IN_CSV_LOOKUP_TABLES_DIR =
- P-T_ABBR =
- Field_datatype =
- Field_name =
- linkbuilder_geo =
- LinkBuilderNonGeo =

INPUT (input)
    -> AttributeExposer_4
AttributeExposer_4
    ATTR_LIST = assetType,resource.id,childViews{},title,title_fr,columns{}
    -> UUIDGenerator_4
Note: Uniquemt quand de la donnée est chargée dans socrata
Tester_4
    BOOL_OP = OR
    COMPOSITE_TEST = 1
    TEST_CLAUSE = TEST @Value(_element_count) != 0
    TEST_MODE = TEST
    PASSED -> UUIDGenerator
UUIDGenerator
    UUID_ATTR = _sub_uuid
    -> AttributeRemover_2
    -> AttributeKeeper
AttributeRemover_2
    LIST_ATTRS = columns{}
    -> FeatureMerger_6 [REQUESTOR]
AttributeKeeper
    KEEP_ATTRS = _sub_uuid
    KEEP_LIST = columns{}
    -> ListExploder
ListExploder
    ATTR_ACCUM_MODE = Merge List Attributes
    ATTR_CONFLICT_RES = Use List Attribute Values
    INDEX_ATTR = _element_index
    LIST_ATTR = columns{}
    ELEMENTS -> FeatureMerger_3 [REQUESTOR]
Note: field datatype
LOOKUP_TABLES_READER_NG
    CSV_ENCODING = utf-8
    CSV_PATH = $(IN_CSV_LOOKUP_TABLES_DIR)
    FEATURE_TYPE = $(Field_datatype)
    PT = $(P-T_ABBR)
    -> AttributeExposer_6
AttributeExposer_6
    ATTR_LIST = datatype,fgp_publish
    -> FeatureMerger_3 [SUPPLIER]
FeatureMerger_3
    ATTR_ACCUM_MODE = Merge Supplier
    ATTR_CONFLICT_RES = Use Requestor
    IGNORE_NULLS = No
    JOIN_KEYS = @Value(dataTypeName) @Value(datatype) AUTO
    MERGE_TYPE = Attributes Only
    PROCESS_DUPS = NO
    REJECT_NULL_MISSING_KEYS = No
    SUPPLIERS_FIRST = No
    MERGED -> Tester_6
    UNMERGED_REQUESTOR -> DuplicateFilter
    UNMERGED_REQUESTOR -> Tester_6
Tester_6
    BOOL_OP = OR
    COMPOSITE_TEST = 1
    TEST_CLAUSE = CASE_INSENSITIVE_TEST @Value(fgp_publish) = oui
    TEST_MODE = CASE_INSENSITIVE_TEST
    PASSED -> ListBuilder
    FAILED -> StringCaseChanger_2
StringCaseChanger_2
    ATTRCHOICE = Selected Attributes
    ATTRLIST = fieldName
    CHANGE_TYPE = lowercase
    -> AttributeRemover_4
Note: Supprimer le fgp_publish pour prendre le vrai
AttributeRemover_4
    REMOVE_ATTRS = fgp_publish
    -> FeatureMerger_5 [REQUESTOR]
DuplicateFilter
    INPUT_ORDERED_CHOICE = No
    KEYATTR = dataTypeName
    UNIQUE -> Unknown_field_datatype (output)
Unknown_field_datatype (output)
Note: field name
LOOKUP_TABLES_READER_NG_2
    CSV_ENCODING = utf-8
    CSV_PATH = $(IN_CSV_LOOKUP_TABLES_DIR)
    FEATURE_TYPE = $(Field_name)
    PT = $(P-T_ABBR)
    -> AttributeExposer
AttributeExposer
    ATTR_LIST = name
    -> StringCaseChanger
StringCaseChanger
    ATTRCHOICE = Selected Attributes
    ATTRLIST = name
    CHANGE_TYPE = lowercase
    -> AttributeCreator_4
AttributeCreator_4
    ATTR_TABLE = SET_TO fgp_publish = oui
    -> FeatureMerger_5 [SUPPLIER]
FeatureMerger_5
    ATTR_ACCUM_MODE = Merge Supplier
    ATTR_CONFLICT_RES = Use Requestor
    IGNORE_NULLS = No
    JOIN_KEYS = @Value(fieldName) @Value(name) AUTO
    MERGE_TYPE = Attributes Only
    PROCESS_DUPS = NO
    REJECT_NULL_MISSING_KEYS = No
    SUPPLIERS_FIRST = No
    MERGED -> ListBuilder
    UNMERGED_REQUESTOR -> ListBuilder
ListBuilder
    GROUP_BY = _sub_uuid
    LIST_NAME = columns
    -> ListDuplicateRemover
ListDuplicateRemover
    SRC_LIST = columns{}.fieldName
    -> FeatureMerger_6 [SUPPLIER]
FeatureMerger_6
    ATTR_ACCUM_MODE = Merge Supplier
    ATTR_CONFLICT_RES = Use Requestor
    IGNORE_NULLS = No
    JOIN_KEYS = @Value(_sub_uuid) @Value(_sub_uuid) AUTO
    MERGE_TYPE = Attributes Only
    PROCESS_DUPS = NO
    REJECT_NULL_MISSING_KEYS = No
    SUPPLIERS_FIRST = No
    MERGED -> AttributeRemover_3
AttributeRemover_3
    LIST_ATTRS = columns{}._element_index columns{}.datatype columns{}.name
    -> ListSearcher

Bookmark: Extraction des chillds view pour avoir l'info stocké dans socrata direct (Collumns{})
UUIDGenerator_4
    UUID_ATTR = _uuid
    -> FeatureMerger_2 [REQUESTOR]
    -> Tester_2
Note: If childViews{} has a value and URL_VALIDATION = yes
Tester_2
    BOOL_OP = COMPOSITE
    COMPOSITE_TEST = 1 AND 2
    TEST_CLAUSE:
      CASE_INSENSITIVE_TEST childViews{0} ATTRIBUTE_HAS_A_VALUE ""
      CASE_INSENSITIVE_TEST $(URL_VALIDATION) = yes
    TEST_MODE = CASE_INSENSITIVE_TEST
    PASSED -> AttributeKeeper_6
    FAILED -> AttributeCreator_6
AttributeKeeper_6
    KEEP_ATTRS = datatypes_concat,_uuid
    KEEP_LIST = childViews{}
    -> ListExploder_3
ListExploder_3
    ATTR_ACCUM_MODE = Merge List Attributes
    ATTR_CONFLICT_RES = Use List Attribute Values
    INDEX_ATTR = _element_index
    LIST_ATTR = childViews{}
    ELEMENTS -> HTTPCaller_7
    <REJECTED> -> Terminator
HTTPCaller_7
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body2
    TARGET_ATTR_ENCODING = auto-detect
    TARGET_URL = $(DOMAIN)/api/views/@Value(childViews).json
    TRANSFER_TIMEOUT_LENGTH = 90
    USE_COOKIES = No
    VERIFY_SSL_CERTIFICATES = No
    -> JSONFlattener_5
    <REJECTED> -> Cloner_2
JSONFlattener_5
    ERROR_LIST_ATTR = _json_error
    JSON_DOCUMENT = @Value(_response_body2)
    READ_FROM_FILE = NO
    RECURSIVE = Yes
    -> AttributeExposer_11
    <REJECTED> -> Cloner_2
AttributeExposer_11
    ATTR_LIST = columns{}.fieldName,columns{}.dataTypeName,name
    -> AttributeCreator
AttributeCreator
    ATTR_TABLE:
      SET_TO layerid = @Value(childViews)
      SET_TO title = @Value(name)
    -> PythonCaller_3
Cloner_2
    COPIES = 1
    COPYATT = _copynum
Terminator
    MESSAGE = Translation Terminated
AttributeCreator_6
    ATTR_TABLE = SET_TO layerid = @Value(resource.id)
    -> PythonCaller_3
PythonCaller_3
    PYTHONSOURCE:
      import fme
      import fmeobjects
      # Template Function interface:
      # When using this function, make sure its name is set as the value of
      # the 'Class or Function to Process Features' transformer parameter
      def processFeature(feature):
          _list = feature.getAttribute('columns{}.dataTypeName')
          _outlist =  [x.lower() for x in _list]
          for i in range (len(_outlist)):
              feature.setAttribute('columns{{{}}}.dataTypeName'.format(i),_outlist[i])

      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = FeatureProcessor
    -> ListElementCounter
ListElementCounter
    CNT_ATTR = _element_count
    LIST_NAME = columns{}
    -> Tester_4

Bookmark: NB_RESOURCES_MAPPER
ListSearcher
    ATTR_VALUE = oui
    INDEX_ATTR = _list_index
    LIST_ATTR = columns{}.fgp_publish
    MATCHTYPE = FIRST_MATCHED_ENCODED
    FOUND -> AttributeCreator_5
    NOT_FOUND -> FeatureMerger_7 [REQUESTOR]
AttributeCreator_5
    ATTR_TABLE = SET_TO fgp_publish = oui
    -> Tester_7
Note: Call incomplet à L'API. On fait crasher l'appel volontairement mais en fonction du type d'erreur on est en mesure de savoir si c'est geo ou non
Tester_7
    BOOL_OP = OR
    COMPOSITE_TEST = 1
    TEST_CLAUSE = CASE_INSENSITIVE_TEST $(URL_VALIDATION) = yes
    TEST_MODE = CASE_INSENSITIVE_TEST
    PASSED -> HTTPCaller_2
    FAILED -> AttributeManager
Note: if URL_VALIDATION = No; add value 400 to _http_status_code
AttributeManager
    ATTR_TABLE = SET_TO _http_status_code = 400
    -> Junction
Note: LinkBuilderNonGeo
LOOKUP_TABLES_READER_NG_4
    CSV_ENCODING = utf-8
    CSV_PATH = $(IN_CSV_LOOKUP_TABLES_DIR)
    FEATURE_TYPE = $(LinkBuilderNonGeo)
    PT = $(P-T_ABBR)
    -> AttributeExposer_5
AttributeExposer_5
    ATTR_LIST = format,url,titlepart,spatial_type
    -> FeatureMerger [SUPPLIER]
    -> AttributeRemover
    -> FeatureMerger_4 [SUPPLIER]
Note: Transfert des formats non geo sur les features geo
FeatureMerger_4
    ATTR_ACCUM_MODE = Merge Supplier
    ATTR_CONFLICT_RES = Use Requestor
    IGNORE_NULLS = No
    JOIN_KEYS = 1 1 AUTO
    LIST_NAME = api_resources
    MERGE_TYPE = Attributes Only
    PROCESS_DUPS = NO
    REJECT_NULL_MISSING_KEYS = No
    SUPPLIERS_FIRST = No
    MERGED -> ListExploder_5
    UNMERGED_REQUESTOR -> Terminator_2
Note: Pas de spatial type / entité non géo / même si on a mis text table dans le fichier de config
AttributeRemover
    REMOVE_ATTRS = spatial_type
    -> FeatureMerger_7 [SUPPLIER]
Note: Transfert des formats non geo sur les features non geo. pas de spatial type
FeatureMerger_7
    ATTR_ACCUM_MODE = Merge Supplier
    ATTR_CONFLICT_RES = Use Requestor
    IGNORE_NULLS = No
    JOIN_KEYS = 1 1 AUTO
    LIST_NAME = api_resources
    MERGE_TYPE = Attributes Only
    PROCESS_DUPS = NO
    REJECT_NULL_MISSING_KEYS = No
    SUPPLIERS_FIRST = No
    MERGED -> ListExploder_5
    UNMERGED_REQUESTOR -> Terminator_2
Note: linkbuilder_geo
LOOKUP_TABLES_READER_NG_3
    CSV_ENCODING = utf-8
    CSV_PATH = $(IN_CSV_LOOKUP_TABLES_DIR)
    FEATURE_TYPE = $(linkbuilder_geo)
    PT = $(P-T_ABBR)
    -> AttributeExposer_7
AttributeExposer_7
    ATTR_LIST = format,url,titlepart,spatial_type
    -> FeatureMerger [SUPPLIER]
FeatureMerger
    ATTR_ACCUM_MODE = Merge Supplier
    ATTR_CONFLICT_RES = Use Requestor
    IGNORE_NULLS = No
    JOIN_KEYS = 1 1 AUTO
    LIST_NAME = api_resources
    MERGE_TYPE = Attributes Only
    PROCESS_DUPS = NO
    REJECT_NULL_MISSING_KEYS = No
    SUPPLIERS_FIRST = No
    MERGED -> ListExploder_5
    UNMERGED_REQUESTOR -> Terminator_2
ListExploder_5
    ATTR_ACCUM_MODE = Merge List Attributes
    ATTR_CONFLICT_RES = Use List Attribute Values
    INDEX_ATTR = _element_index
    LIST_ATTR = api_resources{}
    ELEMENTS -> StringReplacer_4
    <REJECTED> -> Terminator_2
StringReplacer_4
    CASE = NO
    FIND_TEXT = ($DOMAIN$)
    NO_MATCH = _FME_NO_OP_
    REGEXP = NO
    REPLACE_TEXT = $(DOMAIN)
    SRC_ATTRS = url
    -> StringReplacer_3
StringReplacer_3
    CASE = NO
    FIND_TEXT = ($ID$)
    NO_MATCH = _FME_NO_OP_
    REGEXP = NO
    REPLACE_TEXT = @Value(layerid)
    SRC_ATTRS = url
    -> AttributeCreator_10
AttributeCreator_10
    ATTR_TABLE = SET_TO name = @Value(title) (@Value(titlepart))
    -> Tester
Tester
    BOOL_OP = OR
    COMPOSITE_TEST = 1
    TEST_CLAUSE = TEST @Value(title_fr) != ""
    TEST_MODE = TEST
    PASSED -> AttributeCreator_2
    FAILED -> Tester_3
AttributeCreator_2
    ATTR_TABLE = SET_TO name_fr = @Value(title_fr) (@Value(titlepart))
    -> Tester_3
Tester_3
    BOOL_OP = OR
    COMPOSITE_TEST = 1
    TEST_CLAUSE = CASE_INSENSITIVE_TEST $(URL_VALIDATION) = yes
    TEST_MODE = CASE_INSENSITIVE_TEST
    PASSED -> Tester_8
    FAILED -> FeatureMerger_2 [SUPPLIER]
Tester_8
    BOOL_OP = OR
    COMPOSITE_TEST = 1
    TEST_CLAUSE = TEST status_code_url ATTRIBUTE_IS_MISSING ""
    TEST_MODE = TEST
    PASSED -> Junction_2
    FAILED -> PythonCaller
PythonCaller
    PYTHONSOURCE:
      import fme
      import fmeobjects
      from Python.FME_utils import FME_utils



      class FeatureProcessor(object):
          def __init__(self):
              pass
          def input(self,feature):
              status_code_url=FME_utils.http_check_url_request_options(feature.getAttribute('url'))
              if status_code_url.status_code == 200:
               self.pyoutput(feature)
          def close(self):
              pass
    PYTHONSYMBOL = FeatureProcessor
    -> Junction_2
Junction_2
    -> FeatureMerger_2 [SUPPLIER]
FeatureMerger_2
    ATTR_ACCUM_MODE = Merge Supplier
    ATTR_CONFLICT_RES = Use Requestor
    IGNORE_NULLS = No
    JOIN_KEYS = @Value(_uuid) @Value(_uuid) AUTO
    LIST_ATTRS_TO_INCLUDE = format name url name_fr spatial_type fgp_publish
    LIST_NAME = socrata_db_resources
    MERGE_TYPE = Attributes Only
    PROCESS_DUPS = NO
    REJECT_NULL_MISSING_KEYS = No
    SUPPLIERS_FIRST = No
    MERGED -> ATTRIBUTE_UNEXPOSER
    UNMERGED_REQUESTOR -> ATTRIBUTE_UNEXPOSER
ATTRIBUTE_UNEXPOSER
    -> OUTPUT (output)
OUTPUT (output)
Terminator_2
    MESSAGE = Translation Terminated

Bookmark: Test pour savoir si le call avec /api/geospatial fonctionne
HTTPCaller_2
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = $(DOMAIN)/api/geospatial/@Value(layerid)
    TRANSFER_TIMEOUT_LENGTH = 90
    USE_COOKIES = No
    VERIFY_SSL_CERTIFICATES = No
    <REJECTED> -> Junction
Junction
    -> AttributeExposer_2
AttributeExposer_2
    ATTR_LIST = _http_status_code
    -> Tester_5
Tester_5
    BOOL_OP = OR
    COMPOSITE_TEST = 1
    TEST_CLAUSE = TEST @Value(_http_status_code) = 400
    TEST_MODE = TEST
    PASSED -> FeatureMerger [REQUESTOR]
    PASSED -> FeatureMerger_4 [REQUESTOR]
    FAILED -> FeatureMerger_4 [REQUESTOR]
