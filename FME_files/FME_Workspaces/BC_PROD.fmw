FME workspace BC_PROD.fmw
Title: BC_PROD
Description: Description 
This workbench read and trasform all the metadata for the province of British Columbia (BC)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...). Extracted automatically using a Python script from the name of the FME Workspace (ex.: BC_PROD.fmw)
METADATA_OVERWRITE: Enable the overwite of the PyCSW.  Can take two values: Yes: Overwrite the content of the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
IN_TBS_JSON_TEMPLATE_DIR: Source directory of the root JSON templates. Defined as: \JSON_TEMPLATES
LOG_FILE: Output log file. Defined as: \BC\LOG\BC.log
OUT_JSON_LOCAL_DIR: Source directory to output JSON files. Defined as: \BC\JSON_LOCAL
OUT_XLS_NOTIFICATION: Source directory to output excel files. Defined as: \BC\XLS
OUT_XML_FAILED_DIR: Source directory to output failed XML files. Defined as: \BC\XML_FAILED
OUT_XML_LOCAL_DIR: Source directory to output Local Source XML files. Defined as: \BC\XML_LOCAL
OUT_XML_PASSED_DIR: Source directory to output passedXML files. Defined as: \BC\XML_PASSED
SAMPLE_SIZE: Number of features to process. Zero (0) means process all the features. A number n greater than 0 means sample or process only the first n features.
URL_VALIDATION : Indicates to validate or not created URL. (Should be Yes for prod)
History: Original version,Unknown,Unknown,Terminate Geo processing. Develop Non geo processing.,5/7/2022,Daniel Pilon,
Startup Python:
      import sys
      import fme
      try:
          if fme.macroValues['FME_SHAREDRESOURCE_DATA']:
              new_path='%s\PT_Harvester\Python'%(fme.macroValues['FME_SHAREDRESOURCE_DATA'])

              print ('Ajout de %s dans le path '%(new_path))
              sys.path += [new_path]


      except:
          raise

Parameters:
- ACTIVATE_GEO = Yes
- ACTIVATE_NON_GEO = Yes
- ACTIVATE_TRANSLATION = No
- CATALOGUE_READER_SELECT = No
- FORCED_PYCSW_URL =
- IN_FFS_TESTING_FILE = $(FME_MF_DIR)BC_Catalogue_Reader.ffs
- LOCAL_SOURCE_METADATA_DELTA_FINDER = Yes
- LOCAL_WRITER = Yes
- METADATA_OVERWRITE = YES
- IN_OUT_WORKING_DIR = C:\Data\PT_Harvester
- SAMPLE_SIZE = 10
- URL_VALIDATION = No
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Server Resource Data

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Junction_3
    -> Tester_7
Junction
    -> RESOURCES_VALIDATOR
Note: Validates url, name and format on resources{} list items
RESOURCES_VALIDATOR
    -> METADATA_VALUE_MAPPER_NG_5 [DATA_INPUT]
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
Junction_2
    -> ON_DATE_FORMATTER
Note: Write the JSON files
text_line (writer TEXTLINE_4)
    attributes: text_line_data buffer

Bookmark: Reading BC Geoportal datasets
Note: Start the process
Creator
    GEOMTYPE = Geometry Object
    NUM = 1
    CREATED -> Tester_3
Tester_3
    BOOL_OP = OR
    COMPOSITE_TEST = 1
    TEST_CLAUSE = TEST $(CATALOGUE_READER_SELECT) = Yes
    TEST_MODE = TEST
    PASSED -> Catalogue_Reader
    FAILED -> FeatureReader [INITIATOR]
Note: Reading BC Server CKAN-API
Catalogue_Reader: Catalogue Reader
    CUSTOM_CSW_LIST_NAME = DefaultNoList{}
    CUSTOM_URL = https://catalogue.data.gov.bc.ca/api/3/action
    SOURCE_URL = Manuel
    Résultats -> Recorder [off]
    Résultats -> Junction_8
Note: Reading FFS file
FeatureReader
    ATTR_ACCUM_MODE = Only Use Result
    COMBINE_GEOM = Use Result
    DATASET = $(IN_FFS_TESTING_FILE)
    FFS_USE_SEARCH_ENVELOPE = NO
    FORMAT = FFS
    INTERACT = <No Spatial Filter>
    OUTPUT_FEATURES_DISPLAY = Schema and Data Features
    <OTHER> -> Junction_8

Bookmark: Data extraction
Note: Record when needed the output of the reader
Recorder
    COMPRESSION_LEVEL = 6
    CREATE_SPATIAL_INDEX = No
    MODE = RECORD_PASS_THROUGH
    RECFILE = $(FME_MF_DIR)BC_Catalogue_Reader.ffs
    STORE_SCANNED_METADATA = No
    STORE_SCANNED_SCHEMA = No
Junction_8
    -> ATTRIBUTE_VALUE_TEXT_CLEANER
Note: Edit date fields; Check for empty resources; Flatten JSON contacts
BC_ATTRIBUTE_FORMATTER
    -> FORMAT_VALIDATOR
Note: Check if resources{}.format="other" can be modified into a more meaningful format value
EMPTY_FORMAT_MAPPER_NG
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> AttributeExposer_5

Bookmark: Filtering and convertion to inhouse model.
Note: Basic edition (trimming, remove tab, cr/lf) to all fields
ATTRIBUTE_VALUE_TEXT_CLEANER
    -> AttributeExposer_2
Note: Sort the records based on the type of licence (Open source licence or otther)
LICENSE_FILTER_NG
    FEATURE_TYPE = License_BC
    IN_CSV_LOOKUP_TABLES_DIR = $(IN_CSV_LOOKUP_TABLES_DIR)
    LICENSE_ATT = @Value(license_title)
    P-T_ABBR = $(P-T_ABBR)
    LICENSE_FILTER_PASSED -> BC_ATTRIBUTE_FORMATTER
    UNKNOWN_LICENSE -> Unknown_licence (writer XLSXW_1)
Unknown_licence (writer XLSXW_1)
    attributes: license_id string(200), license_title string(200), id string(200)

Bookmark: Manage empty license
AttributeExposer_2
    ATTR_LIST = license_title
    -> NullAttributeMapper
NullAttributeMapper
    ATTRCHOICE = Selected Attributes
    ATTRLIST = license_title
    NEW_VALUE = None
    NULL_TREATMENT = New Value
    SOURCE_ATTR_VAL = Null Empty
    -> LICENSE_FILTER_NG

Bookmark: Attribute Validation
Note: Verfication if URL is valid WMS call for WMS formats
FORMAT_VALIDATOR
    -> EMPTY_FORMAT_MAPPER_NG [DATA_INPUT]

Bookmark: Add geoportal weblink
AttributeExposer_5
    ATTR_LIST = name
    -> GEOPORTAL_WEBLINK_ADDER_NG
Note: Add an html resource
GEOPORTAL_WEBLINK_ADDER_NG
    FEATURE_TYPE = GeoportalWeblink_BC
    IN_CSV_LOOKUP_TABLES_DIR = $(IN_CSV_LOOKUP_TABLES_DIR)
    P-T_ABBR = $(P-T_ABBR)
    URL_VALIDATION = $(URL_VALIDATION)
    WEBLINK_WILDCARD = @Value(name)
    -> DEFAULT_ATTRIBUTE_MAPPER_NG

Bookmark: Default value and date management
Note: Add some defaults attribute values
DEFAULT_ATTRIBUTE_MAPPER_NG
    FEATURE_TYPE = Default_BC
    IN_CSV_LOOKUP_TABLES_DIR = $(IN_CSV_LOOKUP_TABLES_DIR)
    P-T_ABBR = $(P-T_ABBR)
    -> ATTRIBUTE_MANAGER_NG
Note: Manage empty attributes
ATTRIBUTE_MANAGER_NG
    IN_YAML_TEXT:
      resources{}.projection_name:
          action: attribute_not_null
          attr2set: default_projection_name
      #
      resources{}.name:
          action: attribute_not_null
          attr2set: resources{}.description
      #
      resources{}.resource_update_cycle:
          action: attribute_not_null
          attr2set: default_resource_update_cycle
      #
      contacts{}.email:
          action: attribute_not_null
          attr2set: default_contact_email
      #
      resources{}.language:
          action: text_not_null
          attr2set: eng
    -> TEMPORAL_EXTENTS_MAPPER
Note: Maps data collection start and end dates
TEMPORAL_EXTENTS_MAPPER
    -> BC_GEOWAREHOUSE_URL_BUILDER

Bookmark: BC resource formatter
Note: Concatenates URL for BC Geowarehouse download links
BC_GEOWAREHOUSE_URL_BUILDER
    -> BC_WMS_FORMATTER
Note: Concatenates WMS URL's to required WMS format
BC_WMS_FORMATTER
    -> BC_RESOURCE_NAME_CORRECTION
Note: Substitutes resource name with dataset title when resource name is missing
BC_RESOURCE_NAME_CORRECTION
    URL_VALIDATION = $(URL_VALIDATION)
    -> RESOURCE_NAME_UNDERSCORE_REMOVER
Note: Removes all underscores from resources{}.name attributes. Long compounded names joined by underscores in this field can cause display formatting issues when published to the FGP.
RESOURCE_NAME_UNDERSCORE_REMOVER
    DATA_OUTPUT -> URL_HTTPS_MAKER [UUIDGenerator_Input]

Bookmark: https maker
URL_HTTPS_MAKER
    URL_VALIDATION = $(URL_VALIDATION)
    -> AttributeExposer_3

Bookmark: Testing email formats
AttributeExposer_3
    ATTR_LIST = default_contact_email
    -> EMAIL_FORMAT_TESTER
Note: Corrects missing '@' in email addresses and email separated by a comma delimiter
EMAIL_FORMAT_TESTER
    DEFAULT_CONTACT_EMAIL = @Value(default_contact_email)
    -> TOPIC_PARSER

Bookmark: Topic extraction
Note: Parses topics into individual attributes when multiple topics appear as comma separated values
TOPIC_PARSER
    DELIMITER = ,
    -> GEO_NONE_GEO_SELECTOR

Bookmark: Spatial data type management
Note: Sort the features into 2 categories: GEO and NONE GEO
GEO_NONE_GEO_SELECTOR
    CSV_FILE_NAME = GeospatialValidation
    CSV_PATH = $(IN_CSV_LOOKUP_TABLES_DIR)
    CSV_PROVINCE = $(P-T_ABBR)
    YAML_DIRECTIVES:
      resources{}.format:
          domain: lookup_table_format
          spatial_type: if_null_overwrite
          not_found: log
          search_type: equals
      #
      resources{}.bcdc_type:
          domain: [spatial,geographic]
          spatial_type: no_overwrite
          not_found: no_log
          search_type: contains
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: Determine the spatial representation type of datasets for each feature
SPATIAL_TYPE_MAPPER_NG
    FEATURE_TYPE = UUID_Spatial_BC
    IN_CSV_LOOKUP_TABLES_DIR = $(IN_CSV_LOOKUP_TABLES_DIR)
    P-T_ABBR = $(P-T_ABBR)
    DATA_OUTPUT_FAILED -> SPATIAL_TYPE_NOT_MAPPED (writer XLSXW_1)
    DATA_OUTPUT_PASSED -> Junction_3
SPATIAL_TYPE_NOT_MAPPED (writer XLSXW_1)
GEOSPATIAL_FORMAT_NOT_MAPPED (writer XLSXW_1)
    attributes: _geo_none_geo_status string(200), id string(200), _not_found_err_msg string(200), format string(200)
Note: Use CSV table to determine the spatial representation type of datasets
MANUAL_GEOSPATIAL_SETTER_NG
    FEATURE_TYPE = UnmappedGeoData_BC
    IN_CSV_LOOKUP_TABLES_DIR = $(IN_CSV_LOOKUP_TABLES_DIR)
    P-T_ABBR = $(P-T_ABBR)
    GEOSPATIAL -> Junction_3
    NON-GEOSPATIAL -> Tester_4
    UNMAPPED_DATA -> unknow_geo_non_geo (writer XLSXW_1)
unknow_geo_non_geo (writer XLSXW_1)
    attributes: id string(200), notes string(200), title string(200), url string(200)

Bookmark: Activate Geo and Sample or full content
Note: GEO activated?
Tester_7
    BOOL_OP = OR
    COMPOSITE_TEST = 1
    TEST_CLAUSE = TEST @UpperCase($(ACTIVATE_GEO)) = YES
    TEST_MODE = TEST
    PASSED -> TestFilter
TestFilter
    DEFAULT_VALUE = SAMPLES FEATURES
    TEST_LIST = "BOOL_OP,OR,COMPOSITE_TEST,""""""1"""""",TEST_CLAUSE,TEST $(SAMPLE_SIZE) = 0",ALL FEATURES
    ALL FEATURES -> Junction
    SAMPLES FEATURES -> Sampler_3
Sampler_3
    RATE = $(SAMPLE_SIZE)
    SAMPLE_MODE = No
    SAMPLE_TYPE_LONG = First N Features
    SAMPLED -> Junction

Bookmark: Attribute value mapper
Note: Maps role to HNAP standards
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
METADATA_VALUE_MAPPER_NG_5
    ATT_TO_MAP = contacts{}.role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_8 [DATA_INPUT]
Note: Maps spatial representation types to HNAP standards
METADATA_VALUE_MAPPER_NG_8
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_11 [DATA_INPUT]
Note: Maps progress code to HNAP standards
METADATA_VALUE_MAPPER_NG_11
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_10 [DATA_INPUT]
Note: Maps update cycle to HNAP standards
METADATA_VALUE_MAPPER_NG_10
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_FORMAT_MAPPER_NG_3 [DATA_INPUT]

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
Note: Map resources.format to HNAP standards
METADATA_FORMAT_MAPPER_NG_3
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> METADATA_FORMAT_MAPPER_NG_2 [DATA_INPUT]
Note: Maps format
METADATA_FORMAT_MAPPER_NG_2
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = NO
    RES_TYPE_FR_REFRESH = NO
    -> METADATA_VALUE_MAPPER_ERROR_MANAGER

Bookmark: Mapping error list creator
Note: Creates list of errors found and not corrected in mapping
METADATA_VALUE_MAPPER_ERROR_MANAGER
    ERROR_OUTPUT -> METADATA_MAPPING_ERRORS (writer XLSXW_1)
    DATA_OUTPUT -> REMOVE_BROKEN_URL_WMS_ESRI_REST
METADATA_MAPPING_ERRORS (writer XLSXW_1)
    attributes: error string(200), id string(200), _element_index string(200)

Bookmark: Data cleanup. Dropping broken web services
Note: Tests WMS/ESRI_REST resource URL's and removes them where broken
REMOVE_BROKEN_URL_WMS_ESRI_REST
    URL_VALIDATION = $(URL_VALIDATION)
    -> WMS_REST_LANGUAGE_FORMATTER
    FAULTY_URL_OUTPUT -> MAP_SERVICE_URL_ERROR (writer XLSXW_1)
MAP_SERVICE_URL_ERROR (writer XLSXW_1)
    attributes: id string(200), url string(200), format string(200), _url_failure_message string(200)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> AttributeExposer_6

Bookmark: New Bookmark
AttributeExposer_6
    ATTR_LIST = resources{}
    -> ListCopier
ListCopier
    DEST_LIST = distributionList
    SRC_LIST = resources{}
    -> GMD_SECTION_DATA_EXTRACTION
Note: Creates lists and removes duplicates for GMD_Section
GMD_SECTION_DATA_EXTRACTION
    -> PythonCaller_4

Bookmark: Manges Insert/Update/delete
Note: Pregenrate formating for ressources description
PythonCaller_4
    NEW_ATTRIBUTES = resources{}.description_temp
    PYTHONSOURCE:
      import fme
      import fmeobjects
      # Template Function interface:
      # When using this function, make sure its name is set as the value of
      # the 'Class or Function to Process Features' transformer parameter
      def processFeature(feature):


          for i in range(len(feature.getAttribute('resources{}.url'))):
              format=feature.getAttribute('resources{%i}.format'%(i))
              restype=feature.getAttribute('resources{%i}.format_resourceType_en'%(i))
              lang=feature.getAttribute('resources{%i}.language'%(i))

              feature.setAttribute('resources{%i}.description_temp'%(i),'%s;%s;%s'%(restype,format,lang))
    PYTHONSYMBOL = processFeature
    -> AttributeCreator_6
Note: Expose published parameter FORCED_PYCSW_URL
AttributeCreator_6
    ATTR_TABLE = SET_TO csw_url = $(FORCED_PYCSW_URL)
    -> AttributeExposer_13
AttributeExposer_13
    ATTR_LIST = search_criteria_pycsw,csw_url
    -> METADATA_DELTA_FINDER_NG
Note: Searches existing PyCSW for new, updated or obsolete dat
METADATA_DELTA_FINDER_NG
    ABSTRACT_ATT_NEW = notes
    ABSTRACT_ATT_REF = MD_Metadata.identificationInfo.MD_DataIdentification.abstract.CharacterString
    CSW_FILTER = @Value(search_criteria_pycsw)
    CUSTOM_CSW_CKAN_URL = @Value(csw_url)
    DATESTAMP_ATT_NEW = record_last_modified
    DATESTAMP_ATT_REF = MD_Metadata.dateStamp.Date
    ID_ATT_NEW = id
    ID_ATT_REF = MD_Metadata.fileIdentifier.CharacterString
    LOCAL_SOURCE = $(LOCAL_SOURCE_METADATA_DELTA_FINDER)
    LOCAL_SOURCE_DIR = $(OUT_XML_LOCAL_DIR)
    LOCAL_SOURCE_FORMAT = XML
    METADATA_OVERWRITE = $(METADATA_OVERWRITE)
    RES_FORMAT_ATT_NEW = resources{}.description_temp
    RES_FORMAT_ATT_REF = MD_Metadata.distributionInfo.MD_Distribution.transferOptions{}.MD_DigitalTransferOptions.onLine.CI_OnlineResource.description.CharacterString
    RES_NAME_ATT_NEW = resources{}.name
    RES_NAME_ATT_REF = MD_Metadata.distributionInfo.MD_Distribution.transferOptions{}.MD_DigitalTransferOptions.onLine.CI_OnlineResource.name.CharacterString
    RES_URL_ATT_NEW = resources{}.url
    RES_URL_ATT_REF = MD_Metadata.distributionInfo.MD_Distribution.transferOptions{}.MD_DigitalTransferOptions.onLine.CI_OnlineResource.linkage.URL
    TITLE_ATT_NEW = title
    TITLE_ATT_REF = MD_Metadata.identificationInfo.MD_DataIdentification.citation.CI_Citation.title.CharacterString
    Statistics -> StatisticsCalculator_Summary_2
    Update -> Junction_5
    Insert -> Junction_5
Note: Log statistics
StatisticsCalculator_Summary_2: Logger
    LOG_FEATURE = NONE
    MAXFEATS = 20
    MESSAGE:
      ************************
      **** Geo Unchanged Report ****
      ************************

      @Value(_real_count) features were unchanged

      ************************
      ************************
      ************************
    SEVERITY = INFO
Junction_5
    -> AWS_TRANSLATE

Bookmark: Language Translation
Note: Translates specific items from English to French
AWS_TRANSLATE
    ACTIVATE_TRANSLATION = $(ACTIVATE_TRANSLATION)
    ATTR_2_TRANSLATE = notes,title,sector
    ATTR_LIST_2_TRANSLATE = tags{}.display_name,resources{}.name
    MODE = English-->French
    -> XML_PUBLISHER_NG
    TRANSLATION_PROBLEM -> translation_problems (writer XLSXW_1)
translation_problems (writer XLSXW_1)
    attributes: id auto(20)

Bookmark: XML CREATION AND WRITING
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
Note: CSV config file to map BC attributes to those required by the XML templates
XML_PUBLISHER_NG
    FEATURE_TYPE = Config_BC
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = C:\Data\PT_Harvester\XML_TEMPLATES\GMD_CITEDRESPONSIBLEPARTY.xml
    TEMPLATE_GMD_CONTACT = C:\Data\PT_Harvester\XML_TEMPLATES\GMD_CONTACT.xml
    TEMPLATE_GMD_DISTRIBUTIONFORMAT = C:\Data\PT_Harvester\XML_TEMPLATES\GMD_DISTRIBUTIONFORMAT.xml
    TEMPLATE_GMD_DISTRIBUTOR = C:\Data\PT_Harvester\XML_TEMPLATES\GMD_DISTRIBUTOR.xml
    TEMPLATE_GMD_KEYWORDS = C:\Data\PT_Harvester\XML_TEMPLATES\GMD_KEYWORDS.xml
    TEMPLATE_GMD_MDMETADATA = C:\Data\PT_Harvester\XML_TEMPLATES\GMD_MDMETADATA.xml
    TEMPLATE_GMD_REFERENCESYSTEMINFO = C:\Data\PT_Harvester\XML_TEMPLATES\GMD_REFERENCESYSTEMINFO.xml
    TEMPLATE_GMD_RESOURCEMAINTENANCE = C:\Data\PT_Harvester\XML_TEMPLATES\GMD_RESOURCEMAINTENANCE.xml
    TEMPLATE_GMD_TOPICCATEGORY = C:\Data\PT_Harvester\XML_TEMPLATES\GMD_TOPICCATEGORY.xml
    TEMPLATE_GMD_TRANSFEROPTIONS = C:\Data\PT_Harvester\XML_TEMPLATES\GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    UPDATE_FAILED -> text_line (writer TEXTLINE_2)

Bookmark: Activate None Geo and Sample or fulle content
Note: NONE GEO activated?
Tester_4
    BOOL_OP = OR
    COMPOSITE_TEST = 1
    TEST_CLAUSE = TEST @UpperCase($(ACTIVATE_NON_GEO)) = YES
    TEST_MODE = TEST
    PASSED -> TestFilter_2
TestFilter_2
    DEFAULT_VALUE = SAMPLES FEATURES
    TEST_LIST = "BOOL_OP,OR,COMPOSITE_TEST,""""""1"""""",TEST_CLAUSE,TEST $(SAMPLE_SIZE) = 0",ALL FEATURES
    ALL FEATURES -> Junction_2
    SAMPLES FEATURES -> Sampler_4
Sampler_4
    RATE = $(SAMPLE_SIZE)
    SAMPLE_MODE = No
    SAMPLE_TYPE_LONG = First N Features
    SAMPLED -> Junction_2

Bookmark: Non-Geospatial Export
Note: Extracts, sorts, filters and creates data values and addresses areas where date values are missing
ON_DATE_FORMATTER
    -> RESOURCES_VALIDATOR_2
Note: Validates url, name and format on resources{} list items
RESOURCES_VALIDATOR_2
    -> METADATA_VALUE_MAPPER_NG_4 [DATA_INPUT]
Note: Map update_frequency to CKAN
METADATA_VALUE_MAPPER_NG_4
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_4 [DATA_INPUT]
Note: Map resources{}.format to CKAN
METADATA_FORMAT_MAPPER_NG_4
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    -> AttributeExposer_8
Note: Extract errors created by the METADATA_VALUE_MAPPER_NG
METADATA_VALUE_MAPPER_ERROR_MANAGER_2
    ERROR_OUTPUT -> ATTRIBUTE_MAPPING_ERRORS_NONE_GEO (writer XLSXW_1)
    DATA_OUTPUT -> RESOURCE_NAME_UNDERSCORE_REMOVER_2
Note: Removes all underscores from resources{}.name attributes. Long compounded names joined by underscores in this field can cause display formatting issues when published to the FGP.
RESOURCE_NAME_UNDERSCORE_REMOVER_2
    DATA_OUTPUT -> METADATA_DELTA_FINDER_NG_2
Note: Searches existing PyCSW for new, updated or obsolete features
METADATA_DELTA_FINDER_NG_2
    ABSTRACT_ATT_NEW = notes
    ABSTRACT_ATT_REF = notes_translated.en
    DATESTAMP_ATT_NEW = record_last_modified
    DATESTAMP_ATT_REF = federated_date_modified
    ID_ATT_NEW = id
    ID_ATT_REF = id
    LOCAL_SOURCE = Yes
    LOCAL_SOURCE_DIR = $(OUT_JSON_LOCAL_DIR)
    LOCAL_SOURCE_FORMAT = JSON
    METADATA_OVERWRITE = $(METADATA_OVERWRITE)
    RES_FORMAT_ATT_NEW = resources{}.format
    RES_FORMAT_ATT_REF = resources{}.format
    RES_NAME_ATT_NEW = resources{}.format
    RES_NAME_ATT_REF = resources{}.format
    RES_URL_ATT_NEW = resources{}.url
    RES_URL_ATT_REF = resources{}.url
    TITLE_ATT_NEW = title
    TITLE_ATT_REF = title_translated.en
    Statistics -> StatisticsCalculator_Summary_3
    Update -> Junction_4
    Insert -> Junction_4
Note: Log statistics
StatisticsCalculator_Summary_3: Logger
    LOG_FEATURE = NONE
    MAXFEATS = 20
    MESSAGE:
      ************************
      **** None Geo Unchanged Report ****
      ************************

      @Value(_real_count) features were unchanged

      ************************
      ************************
      ************************
    SEVERITY = INFO
Junction_4
    -> AWS_TRANSLATE_3
Note: CSV JSON config file to map BC attributes to those required by the JSON templates
JSON_PUBLISHER_NG
    FEATURE_TYPE = JSON_CONFIG_BC
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name_en
    Keywords_FR = tags{}.display_name_fr
    P-T_ABBR = $(P-T_ABBR)
    Subject_LIST = TBS_Subject{}.value
    Topic_LIST = TBS_Topic{}.value
    OUTPUT_LOCAL -> AttributeExposer_4
AttributeExposer_4
    ATTR_LIST = json_file,id
    -> AttributeCreator_2
AttributeCreator_2
    ATTR_TABLE = SET_TO text_line_data = @Value(json_file)
    -> text_line (writer TEXTLINE_4)
ATTRIBUTE_MAPPING_ERRORS_NONE_GEO (writer XLSXW_1)
    attributes: error string(200), id string(200), _element_index string(200)

Bookmark: Extraction of the subject
AttributeExposer_8
    ATTR_LIST = extras{}.key,extras{}.value
    -> ListSearcher_2
Note: Extract the subject from key/value list
ListSearcher_2
    ATTR_VALUE = sector
    INDEX_ATTR = _list_index
    LIST_ATTR = extras{}.key
    MATCHTYPE = REGULAR_EXPRESSION_ENCODED
    PREFIX = topic_
    FOUND -> Junction_6
    NOT_FOUND -> AttributeCreator
Note: Manage empty subject
AttributeCreator
    ATTR_TABLE = SET_TO topic_value = government_and_politics
    -> Junction_6
Junction_6
    -> AttributeCreator_7
AttributeCreator_7
    ATTR_TABLE = SET_TO TBS_Subject{0}.value = @Value(topic_value)
    -> AttributeRemover
AttributeRemover
    REMOVE_ATTRS = _list_index,topic_key
    -> METADATA_VALUE_MAPPER_NG_9 [DATA_INPUT]

Bookmark: Generating TBS_SUBJECT list based on tags
Note: Map TBS_Subject{}.value to CKAN
METADATA_VALUE_MAPPER_NG_9
    ATT_TO_MAP = TBS_Subject{}.value
    CODE_REFRESH = NO
    ENGLISH_REFRESH = YES
    ERROR_NOT_MAPPED = NO
    FEATURE_TYPE = Subject_TBS_BC
    FRENCH_REFRESH = NO
    IN_CSV_LOOKUP_TABLES_DIR = $(IN_CSV_LOOKUP_TABLES_DIR)
    P-T_ABBR = $(P-T_ABBR)
    -> AttributeExposer_14

Bookmark: Remove duplicate subject
AttributeExposer_14
    ATTR_LIST = TBS_Subject{}.value
    -> ListDuplicateRemover
ListDuplicateRemover
    SRC_LIST = TBS_Subject{}.value
    -> AttributeExposer_10

Bookmark: Extraction of the topic
AttributeExposer_10
    ATTR_LIST = extras{}.key,extras{}.value
    -> ListSearcher_4
Note: Extract the topic from key/value list
ListSearcher_4
    ATTR_VALUE = sector
    INDEX_ATTR = _list_index
    LIST_ATTR = extras{}.key
    MATCHTYPE = REGULAR_EXPRESSION_ENCODED
    PREFIX = topic_
    FOUND -> Junction_7
    NOT_FOUND -> AttributeCreator_10
Note: Manage empty topic
AttributeCreator_10
    ATTR_TABLE = SET_TO topic_value = geoscientific_information
    -> Junction_7
Junction_7
    -> AttributeCreator_11
AttributeCreator_11
    ATTR_TABLE = SET_TO TBS_Topic{0}.value = @Value(topic_value)
    -> METADATA_VALUE_MAPPER_NG_6 [DATA_INPUT]

Bookmark: Generating Tbs Topic based on tags
Note: Map TBS_Subject{}.value to CKAN
METADATA_VALUE_MAPPER_NG_6
    ATT_TO_MAP = TBS_Topic{}.value
    CODE_REFRESH = NO
    ENGLISH_REFRESH = YES
    ERROR_NOT_MAPPED = YES
    FEATURE_TYPE = Topic_TBS_BC
    FRENCH_REFRESH = NO
    IN_CSV_LOOKUP_TABLES_DIR = $(IN_CSV_LOOKUP_TABLES_DIR)
    P-T_ABBR = $(P-T_ABBR)
    -> AttributeExposer_15

Bookmark: Remove duplicate topic
AttributeExposer_15
    ATTR_LIST = TBS_Topic{}.value
    -> ListDuplicateRemover_2
ListDuplicateRemover_2
    SRC_LIST = TBS_Topic{}.value
    -> METADATA_VALUE_MAPPER_ERROR_MANAGER_2

Bookmark: Language translation
Note: Translate some attributes using AWS translate
AWS_TRANSLATE_3
    ACTIVATE_TRANSLATION = $(ACTIVATE_TRANSLATION)
    ATTR_2_TRANSLATE = notes,title
    ATTR_LIST_2_TRANSLATE = tags{}.display_name,resources{}.name
    MODE = English-->French
    -> JSON_PUBLISHER_NG
    TRANSLATION_PROBLEM -> TRANSLATION_PROBLEM_NONE_GEO (writer XLSXW_1)
TRANSLATION_PROBLEM_NONE_GEO (writer XLSXW_1)
    attributes: _aws_activation string(200), _mode string(200), _attr2translate string(200), _attrlist2translate string(200), _translation_status string(200)
