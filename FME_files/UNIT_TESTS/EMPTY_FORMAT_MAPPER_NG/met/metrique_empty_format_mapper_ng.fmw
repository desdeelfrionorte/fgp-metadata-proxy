FME workspace metrique_empty_format_mapper_ng.fmw

Parameters:
- OUT_FFS_FILE = resul1.ffs
- LOG_FILE = log
- FEATURE_TYPE = Format
- TEXT = Mime_type   # CSV_MIME_TYPE CSV MIME TYPE
- IN_CSV_LOOKUP_TABLES_DIR = .
- P-T_ABBR = SK
- URL_VALIDATION = Yes

Writers:
- FFS_1: FFS to $(OUT_FFS_FILE)

EMPTY_FORMAT_MAPPER_NG
    CSV_FORMAT = $(FEATURE_TYPE)
    CSV_MIME_TYPE = $(CSV_MIME_TYPE)
    IN_CSV_LOOKUP_TABLES_DIR = $(IN_CSV_LOOKUP_TABLES_DIR)
    P-T_ABBR = $(P-T_ABBR)
    URL_VALIDATION = $(URL_VALIDATION)
    DATA_OUTPUT -> out_ffs (writer FFS_1)
out_ffs (writer FFS_1)

Bookmark: Test#1
Note: Test where the resource has not url
Creator
    GEOMTYPE = Geometry Object
    NUM = 1
    CREATED -> AttributeCreator
AttributeCreator
    ATTR_TABLE = SET_TO resources{0}.format = html
    -> EMPTY_FORMAT_MAPPER_NG [DATA_INPUT]

Bookmark: Test#2
Note: Test where there is not format and it is extracted from the url
Creator_2
    GEOMTYPE = Geometry Object
    NUM = 1
    CREATED -> AttributeCreator_2
AttributeCreator_2
    ATTR_TABLE:
      SET_TO resources{0}.url = http://www.gov.pe.ca/photos/original/CorporateLanduseInventory2010.MIF.zip
      SET_TO resources{1}.url = http://www.gov.pe.ca/photos/original/1958_forest.SHP.zip
      SET_TO resources{2}.url = http://www.gov.pe.ca/photos/original/mast_str_guide.TXT.zip
      SET_TO resources{3}.url = http://www.gov.pe.ca/photos/original/Wetlands09.DXF.zip
    -> EMPTY_FORMAT_MAPPER_NG [DATA_INPUT]

Bookmark: Test#3
Note: Test for WMS, ESRI REST or url without file extention
Creator_3
    GEOMTYPE = Geometry Object
    NUM = 1
    CREATED -> AttributeCreator_3
AttributeCreator_3
    ATTR_TABLE:
      SET_TO resources{0}.url = https://data.princeedwardisland.ca/api/views/djya-sxer/rows.csv?service=wms_accessType=DOWNLOAD
      SET_TO resources{1}.url = http://www.gov.pe.ca/photos/original/mapserver/Building_Outlines_Oct_2003_Polygon.zip
      SET_TO resources{2}.url = http://www.gov.pe.ca/photos/original/featureserver/Building_Outlines_Oct_2003_Polygon.zip
      SET_TO resources{3}.url = http://www.gov.pe.ca/photos/original/DummyFileExtention.DYF.zip
    -> EMPTY_FORMAT_MAPPER_NG [DATA_INPUT]

Bookmark: Test#4
Note: Test whee dash (-) and underscore (_) must be replaced by dot (.) in the url to identify the format
Creator_4
    GEOMTYPE = Geometry Object
    NUM = 1
    CREATED -> AttributeCreator_4
AttributeCreator_4
    ATTR_TABLE:
      SET_TO resources{0}.url = http://www.gov.pe.ca/photos/original/hiddenFileExtention-DXF.zip
      SET_TO resources{1}.url = http://www.gov.pe.ca/photos/original/hiddenFileExtention_DXF.zip
      SET_TO resources{2}.url = http://www.gov.pe.ca/photos/original/WithoutOtherExtention.zip
      SET_TO resources{3}.url = http://www.gov.pe.ca/photos/original/TooLargeToBe_Extention.zip
    -> EMPTY_FORMAT_MAPPER_NG [DATA_INPUT]

Bookmark: Test#5
Note: Test where the format is already 'other'
Creator_5
    GEOMTYPE = Geometry Object
    NUM = 1
    CREATED -> AttributeCreator_5
AttributeCreator_5
    ATTR_TABLE:
      SET_TO resources{0}.url = http://www.gov.pe.ca/photos/original/hiddenFileExtention-DXF.zip
      SET_TO resources{0}.format = other
    -> EMPTY_FORMAT_MAPPER_NG [DATA_INPUT]

Bookmark: Test#6
Note: Test using the Mime_type of the url adddress when url_validation is set to True
Creator_6
    GEOMTYPE = Geometry Object
    NUM = 1
    CREATED -> AttributeCreator_6
AttributeCreator_6
    ATTR_TABLE:
      SET_TO resources{0}.url = http://www.gov.pe.ca/photos/original/application/pdf
      SET_TO resources{0}.format = other
    -> EMPTY_FORMAT_MAPPER_NG [DATA_INPUT]
